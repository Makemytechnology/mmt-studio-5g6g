-- ASN1START

-- **************************************************************
--
-- PDU definitions for NGAP.
--

-- **************************************************************

NGAP-PDU-Contents {
itu-t (0) identified-organization (4) etsi (0) mobileDomain (0)
ngran-Access (22) modules (3) ngap (1) version1 (1) ngap-PDU-Contents (1) }

DEFINITIONS AUTOMATIC TAGS ::=

BEGIN

-- **************************************************************
--
-- IE parameter types from other modules.
--
-- **************************************************************

IMPORTS

A2X-PC5-QoS-Parameters,

AerialUEsubscriptionInformation,

AdditionalULI,

AIoT-CorrelationIdentifier,

AIOTFIdentifier,

AIOTFName,

AIOTSessionReleaseCommandTransfer,

AIOTSessionReleaseCompleteTransfer,

AIOTSessionReleaseRequestTransfer,

AIoT-Support,

AllowedNSSAI,

AMFName,

AMFSetID,

AMF-TNLAssociationSetupList,

AMF-TNLAssociationToAddList,

AMF-TNLAssociationToRemoveList,

AMF-TNLAssociationToUpdateList,

AMF-UE-NGAP-ID,

AssistanceDataForPaging,

AssociatedSessionID,

AUN3DeviceAccessInfo,

AuthenticatedIndication,

BroadcastCancelledAreaList,

BroadcastCompletedAreaList,

BroadcastTransportFailureTransfer,

BroadcastTransportRequestTransfer,

BroadcastTransportResponseTransfer,

CancelAllWarningMessages,

Cause,

CellIDListForRestart,

CEmodeBrestricted,

CEmodeBSupport-Indicator,

CNAssistedRANTuning,

CommandRequestTransfer,

CommandResponseTransfer,

CommandFailureTransfer, ConcurrentWarningMessageInd,

CoreNetworkAssistanceInformationForInactive,

CPTransportLayerInformation,

CriticalityDiagnostics,

DataCodingScheme,

DirectForwardingPathAvailability,

DL-CP-SecurityInformation,

DL-Signalling,

EarlyStatusTransfer-TransparentContainer,

EDT-Session,

EmergencyAreaIDListForRestart,

EmergencyFallbackIndicator,

EN-DCSONConfigurationTransfer,

EndIndication,

Enhanced-CoverageRestriction,

ERedCapIndication,

EUTRA-CGI,

EUTRA-PagingeDRXInformation,

Extended-AMFName,

Extended-ConnectedTime,

Extended-RANNodeName,

FiveGCAction,

FiveG-ProSeAuthorized,

FiveG-ProSePC5QoSParameters,

FiveG-S-TMSI,

GlobalRANNodeID,

GUAMI,

GUAMIList,

GUAMIType,

GW-Context-Release-Indication,

HandoverFlag,

HandoverType,

IAB-Authorized,

IABNodeIndication,

IAB-Supported,

IMSVoiceSupportIndicator,

IndexToRFSP,

InfoOnRecommendedCellsAndRANNodesForPaging,

IntersystemSONConfigurationTransfer,

InventoryRequestTransfer,

InventoryResponseTransfer,

InventoryFailureTransfer,

InventoryReportTransfer,

LAI,

LocationReportingRequestType,

LPWUSPSAssistanceInformation,

LPWUSDisableIndication,

LTE-A2X-ServicesAuthorized,

LTEM-Indication,

LTEUESidelinkAggregateMaximumBitrate,

LTEV2XServicesAuthorized,

MaskedIMEISV,

MBS-AreaSessionID,

MBS-DistributionReleaseRequestTransfer,

MBS-DistributionSetupRequestTransfer,

MBS-DistributionSetupResponseTransfer,

MBS-DistributionSetupUnsuccessfulTransfer,

MBS-ServiceArea,

MBS-SessionID,

MBSSessionReleaseResponseTransfer,

MBSSessionSetupOrModFailureTransfer,

MBSSessionSetupOrModRequestTransfer,

MBSSessionSetupOrModResponseTransfer,

MDTPLMNList,

MDTPLMNModificationList,

MessageIdentifier,

MobileIAB-Authorized,

MobileIABNodeIndication,

MobileIAB-Supported,

MobilityRestrictionList,

MulticastGroupPagingAreaList,

MulticastSessionActivationRequestTransfer,

MulticastSessionDeactivationRequestTransfer,

MulticastSessionUpdateRequestTransfer,

NAS-PDU,

NASSecurityParametersFromNGRAN,

NB-IoT-DefaultPagingDRX,

NB-IoT-PagingDRX,

NB-IoT-Paging-eDRXInfo,

NB-IoT-UEPriority,

NetworkControlledRepeaterAuthorized,

NewSecurityContextInd,

NGRAN-CGI,

NGRAN-TNLAssociationToRemoveList,

NGRANTraceID,

NID,

NoPDUSessionIndication,

NotifySourceNGRANNode,

NPN-AccessInformation,

NR-A2X-ServicesAuthorized,

NR-CGI,

NR-PagingeDRXInformation,

NRPPa-PDU,

NRUESidelinkAggregateMaximumBitrate,

NRV2XServicesAuthorized,

NumberOfBroadcastsRequested,

OverloadResponse,

OverloadStartNSSAIList,

PagingAssisDataforCEcapabUE,

PagingCause,

PagingDRX,

PagingOrigin,

PagingPolicyDifferentiation,

PagingPriority,

Partially-Allowed-NSSAI,

PC5QoSParameters,

PDUSessionAggregateMaximumBitRate,

PDUSessionListMTCommHReq,

PDUSessionResourceAdmittedList,

PDUSessionResourceFailedToModifyListModCfm,

PDUSessionResourceFailedToModifyListModRes,

PDUSessionResourceFailedToResumeListRESReq,

PDUSessionResourceFailedToResumeListRESRes,

PDUSessionResourceFailedToSetupListCxtFail,

PDUSessionResourceFailedToSetupListCxtRes,

PDUSessionResourceFailedToSetupListHOAck,

PDUSessionResourceFailedToSetupListPSReq,

PDUSessionResourceFailedToSetupListSURes,

PDUSessionResourceHandoverList,

PDUSessionResourceListCxtRelCpl,

PDUSessionResourceListCxtRelReq,

PDUSessionResourceListHORqd,

PDUSessionResourceModifyListModCfm,

PDUSessionResourceModifyListModInd,

PDUSessionResourceModifyListModReq,

PDUSessionResourceModifyListModRes,

PDUSessionResourceNotifyList,

PDUSessionResourceReleasedListNot,

PDUSessionResourceReleasedListPSAck,

PDUSessionResourceReleasedListPSFail,

PDUSessionResourceReleasedListRelRes,

PDUSessionResourceResumeListRESReq,

PDUSessionResourceResumeListRESRes,

PDUSessionResourceSecondaryRATUsageList,

PDUSessionResourceSetupListCxtReq,

PDUSessionResourceSetupListCxtRes,

PDUSessionResourceSetupListHOReq,

PDUSessionResourceSetupListSUReq,

PDUSessionResourceSetupListSURes,

PDUSessionResourceSuspendListSUSReq,

PDUSessionResourceSwitchedList,

PDUSessionResourceToBeSwitchedDLList,

PDUSessionResourceToReleaseListHOCmd,

PDUSessionResourceToReleaseListRelCmd,

PEIPSassistanceInformation,

PLMNIdentity,

PLMNSupportList,

PrivacyIndicator,

PWSFailedCellIDList,

QMCConfigInfo,

QMCDeactivation,

RAN-AIOT-Device-NGAP-ID,

RANNodeName,

RANPagingPriority,

RANStatusTransfer-TransparentContainer,

RANTimingSynchronisationStatusInfo,

RAN-TSSRequestType,

RAN-TSSScope,

RAN-UE-NGAP-ID,

RedCapIndication,

RedirectionVoiceFallback,

RelativeAMFCapacity,

RepetitionPeriod,

RequestedNSSAI,

ResetType,

RGLevelWirelineAccessCharacteristics,

RIMInformationTransfer,

RoutingID,

RRCEstablishmentCause,

RRCInactiveTransitionReportRequest,

RRCState,

SecurityContext,

SecurityKey,

SerialNumber,

ServedGUAMIList,

SliceSupportList,

SLPositioningRangingServiceInfo,

S-NSSAI,

SONConfigurationTransfer,

SourceToTarget-AMFInformationReroute,

SourceToTarget-TransparentContainer,

SRVCCOperationPossible,

SupportedTAList,

Suspend-Request-Indication,

Suspend-Response-Indication,

TAI,

TAIListForPaging,

TAIListForRestart,

TargetID,

TargetNSSAIInformation,

TargettoSource-Failure-TransparentContainer,

TargetToSource-TransparentContainer,

TimeSyncAssistanceInfo,

TimeToWait,

TNLAssociationList,

TraceActivation,

TrafficLoadReductionIndication,

TransportLayerAddress,

UEAggregateMaximumBitRate,

UE-associatedLogicalNG-connectionList,

UECapabilityInfoRequest,

UEContextRequest,

UE-DifferentiationInfo,

UE-NGAP-IDs,

UEPagingIdentity,

UEPresenceInAreaOfInterestList,

UERadioCapability,

UERadioCapabilityForPaging,

UERadioCapabilityID,

UERetentionInformation,

UESecurityCapabilities,

UESliceMaximumBitRateList,

UE-UP-CIoT-Support,

UL-CP-SecurityInformation,

UnavailableGUAMIList,

URI-address,

UserLocationInformation,

WarningAreaCoordinates,

WarningAreaList,

WarningMessageContents,

WarningSecurityInfo,

WarningType,

WUS-Assistance-Information,

XrDeviceWith2Rx

FROM NGAP-IEs

PrivateIE-Container{},

ProtocolExtensionContainer{},

ProtocolIE-Container{},

ProtocolIE-ContainerList{},

ProtocolIE-ContainerPair{},

ProtocolIE-SingleContainer{},

NGAP-PRIVATE-IES,

NGAP-PROTOCOL-EXTENSION,

NGAP-PROTOCOL-IES,

NGAP-PROTOCOL-IES-PAIR

FROM NGAP-Containers

id-A2X-PC5-QoS-Parameters,

id-AerialUEsubscriptionInformation,

id-AdditionalULI,

id-AIoT-CorrelationIdentifier,

id-AIOTFIdentifier,

id-AIOTFName,

id-AIOTSessionReleaseCommandTransfer,

id-AIOTSessionReleaseCompleteTransfer,

id-AIOTSessionReleaseRequestTransfer,

id-AIoT-Support,

id-AllowedNSSAI,

id-AMFName,

id-AMFOverloadResponse,

id-AMFSetID,

id-AMF-TNLAssociationFailedToSetupList,

id-AMF-TNLAssociationSetupList,

id-AMF-TNLAssociationToAddList,

id-AMF-TNLAssociationToRemoveList,

id-AMF-TNLAssociationToUpdateList,

id-AMFTrafficLoadReductionIndication,

id-AMF-UE-NGAP-ID,

id-AMF-UE-NGAP-ID2,

id-AssistanceDataForPaging,

id-AssociatedSessionID,

id-AUN3DeviceAccessInfo,

id-AuthenticatedIndication,

id-BroadcastCancelledAreaList,

id-BroadcastCompletedAreaList,

id-BroadcastTransportFailureTransfer,

id-BroadcastTransportRequestTransfer,

id-BroadcastTransportResponseTransfer,

id-CancelAllWarningMessages,

id-Cause,

id-CellIDListForRestart,

id-CEmodeBrestricted,

id-CEmodeBSupport-Indicator,

id-CNAssistedRANTuning,

id-CommandRequestTransfer,

id-CommandResponseTransfer,

id-CommandFailureTransfer,

id-ConcurrentWarningMessageInd,

id-CoreNetworkAssistanceInformationForInactive,

id-CriticalityDiagnostics,

id-DataCodingScheme,

id-DefaultPagingDRX,

id-DirectForwardingPathAvailability,

id-DL-CP-SecurityInformation,

id-DL-Signalling,

id-EarlyStatusTransfer-TransparentContainer,

id-EDT-Session,

id-EmergencyAreaIDListForRestart,

id-EmergencyFallbackIndicator,

id-ENDC-SONConfigurationTransferDL,

id-ENDC-SONConfigurationTransferUL,

id-EndIndication,

id-Enhanced-CoverageRestriction,

id-ERedCapIndication,

id-EUTRA-CGI,

id-EUTRA-PagingeDRXInformation,

id-Extended-AMFName,

id-Extended-ConnectedTime,

id-Extended-RANNodeName,

id-FiveGCAction,

id-FiveG-ProSeAuthorized,

id-FiveG-ProSePC5QoSParameters,

id-FiveG-ProSeUEPC5AggregateMaximumBitRate,

id-FiveG-S-TMSI,

id-GlobalRANNodeID,

id-GUAMI,

id-GUAMIList,

id-GUAMIType,

id-GW-Context-Release-Indication,

id-HandoverFlag,

id-HandoverType,

id-IAB-Authorized,

id-IABNodeIndication,

id-IAB-Supported,

id-IMSVoiceSupportIndicator,

id-IndexToRFSP,

id-InfoOnRecommendedCellsAndRANNodesForPaging,

id-IntersystemSONConfigurationTransferDL,

id-IntersystemSONConfigurationTransferUL,

id-InventoryRequestTransfer,

id-InventoryResponseTransfer,

id-InventoryFailureTransfer,

id-InventoryReportTransfer,

id-LocationReportingRequestType,

id-LPWUSPSAssistanceInformation,

id-LPWUSDisableIndication,

id-LTE-A2X-ServicesAuthorized,

id-LTE-A2X-UE-PC5-AggregateMaximumBitRate,

id-LTEM-Indication,

id-LTEUESidelinkAggregateMaximumBitrate,

id-LTEV2XServicesAuthorized,

id-ManagementBasedMDTPLMNList,

id-ManagementBasedMDTPLMNModificationList,

id-MaskedIMEISV,

id-MBS-AreaSessionID,

id-MBS-DistributionReleaseRequestTransfer,

id-MBS-DistributionSetupRequestTransfer,

id-MBS-DistributionSetupResponseTransfer,

id-MBS-DistributionSetupUnsuccessfulTransfer,

id-MBS-ServiceArea,

id-MBS-SessionID,

id-MBSSessionModificationFailureTransfer,

id-MBSSessionModificationRequestTransfer,

id-MBSSessionModificationResponseTransfer,

id-MBSSessionReleaseResponseTransfer,

id-MBSSessionSetupFailureTransfer,

id-MBSSessionSetupRequestTransfer,

id-MBSSessionSetupResponseTransfer,

id-MessageIdentifier,

id-MobileIAB-Authorized,

id-MobileIABNodeIndication,

id-MobileIAB-Supported,

id-MobilityRestrictionList,

id-MulticastGroupPagingAreaList,

id-MulticastSessionActivationRequestTransfer,

id-MulticastSessionDeactivationRequestTransfer,

id-MulticastSessionUpdateRequestTransfer,

id-NASC,

id-NAS-PDU,

id-NASSecurityParametersFromNGRAN,

id-NB-IoT-DefaultPagingDRX,

id-NB-IoT-PagingDRX,

id-NB-IoT-Paging-eDRXInfo,

id-NB-IoT-UEPriority,

id-NetworkControlledRepeaterAuthorized,

id-NewAMF-UE-NGAP-ID,

id-NewGUAMI,

id-NewSecurityContextInd,

id-NGAP-Message,

id-NGRAN-CGI,

id-NGRAN-TNLAssociationToRemoveList,

id-NGRANTraceID,

id-NoPDUSessionIndication,

id-NotifySourceNGRANNode,

id-NPN-AccessInformation,

id-NR-A2X-ServicesAuthorized,

id-NR-A2X-UE-PC5-AggregateMaximumBitRate,

id-NR-PagingeDRXInformation,

id-NRPPa-PDU,

id-NRUESidelinkAggregateMaximumBitrate,

id-NRV2XServicesAuthorized,

id-NumberOfBroadcastsRequested,

id-OldAMF,

id-OverloadStartNSSAIList,

id-PagingAssisDataforCEcapabUE,

id-PagingCause,

id-PagingDRX,

id-PagingOrigin,

id-PagingPolicyDifferentiation,

id-PagingPriority,

id-Partially-Allowed-NSSAI,

id-PC5QoSParameters,

id-PDUSessionListMTCommHReq,

id-PDUSessionResourceAdmittedList,

id-PDUSessionResourceFailedToModifyListModCfm,

id-PDUSessionResourceFailedToModifyListModRes,

id-PDUSessionResourceFailedToResumeListRESReq,

id-PDUSessionResourceFailedToResumeListRESRes,

id-PDUSessionResourceFailedToSetupListCxtFail,

id-PDUSessionResourceFailedToSetupListCxtRes,

id-PDUSessionResourceFailedToSetupListHOAck,

id-PDUSessionResourceFailedToSetupListPSReq,

id-PDUSessionResourceFailedToSetupListSURes,

id-PDUSessionResourceHandoverList,

id-PDUSessionResourceListCxtRelCpl,

id-PDUSessionResourceListCxtRelReq,

id-PDUSessionResourceListHORqd,

id-PDUSessionResourceModifyListModCfm,

id-PDUSessionResourceModifyListModInd,

id-PDUSessionResourceModifyListModReq,

id-PDUSessionResourceModifyListModRes,

id-PDUSessionResourceNotifyList,

id-PDUSessionResourceReleasedListNot,

id-PDUSessionResourceReleasedListPSAck,

id-PDUSessionResourceReleasedListPSFail,

id-PDUSessionResourceReleasedListRelRes,

id-PDUSessionResourceResumeListRESReq,

id-PDUSessionResourceResumeListRESRes,

id-PDUSessionResourceSecondaryRATUsageList,

id-PDUSessionResourceSetupListCxtReq,

id-PDUSessionResourceSetupListCxtRes,

id-PDUSessionResourceSetupListHOReq,

id-PDUSessionResourceSetupListSUReq,

id-PDUSessionResourceSetupListSURes,

id-PDUSessionResourceSuspendListSUSReq,

id-PDUSessionResourceSwitchedList,

id-PDUSessionResourceToBeSwitchedDLList,

id-PDUSessionResourceToReleaseListHOCmd,

id-PDUSessionResourceToReleaseListRelCmd,

id-PEIPSassistanceInformation,

id-PLMNSupportList,

id-PrivacyIndicator,

id-PWSFailedCellIDList,

id-QMCConfigInfo,

id-QMCDeactivation,

id-RAN-AIOT-Device-NGAP-ID,

id-RANNodeName,

id-RANPagingPriority,

id-RANStatusTransfer-TransparentContainer,

id-RANTimingSynchronisationStatusInfo,

id-RAN-TSSRequestType,

id-RAN-TSSScope,

id-RAN-UE-NGAP-ID,

id-RedCapIndication,

id-RedirectionVoiceFallback,

id-RelativeAMFCapacity,

id-RepetitionPeriod,

id-RequestedNSSAI,

id-ResetType,

id-RGLevelWirelineAccessCharacteristics,

id-RIMInformationTransfer,

id-RoutingID,

id-RRCEstablishmentCause,

id-RRCInactiveTransitionReportRequest,

id-RRC-Resume-Cause,

id-RRCState,

id-SecurityContext,

id-SecurityKey,

id-SelectedNID,

id-SelectedPLMNIdentity,

id-SerialNumber,

id-ServedGUAMIList,

id-SliceSupportList,

id-S-NSSAI,

id-SONConfigurationTransferDL,

id-SONConfigurationTransferUL,

id-SourceAMF-GUAMI,

id-SourceAMF-UE-NGAP-ID,

id-SourceToTarget-AMFInformationReroute,

id-SourceToTarget-TransparentContainer,

id-SRVCCOperationPossible,

id-SupportedTAList,

id-Suspend-Request-Indication,

id-Suspend-Response-Indication,

id-Target-RAN-Node-ID,

id-TAI,

id-TAIListForPaging,

id-TAIListForRestart,

id-TargetID,

id-TargetNSSAIInformation,

id-TargettoSource-Failure-TransparentContainer,

id-TargetToSource-TransparentContainer,

id-TimeSyncAssistanceInfo,

id-TimeToWait,

id-TNGFIdentityInformation,

id-TraceActivation,

id-TraceCollectionEntityIPAddress,

id-TraceCollectionEntityURI,

id-TWIFIdentityInformation,

id-UEAggregateMaximumBitRate,

id-UE-associatedLogicalNG-connectionList,

id-UECapabilityInfoRequest,

id-UEContextRequest,

id-UE-DifferentiationInfo,

id-UE-NGAP-IDs,

id-UEPagingIdentity,

id-UEPresenceInAreaOfInterestList,

id-UERadioCapability,

id-UERadioCapability-EUTRA-Format,

id-UERadioCapabilityForPaging,

id-UERadioCapabilityID,

id-UERetentionInformation,

id-UESecurityCapabilities,

id-UESliceMaximumBitRateList,

id-UE-UP-CIoT-Support,

id-UL-CP-SecurityInformation,

id-UnavailableGUAMIList,

id-UserLocationInformation,

id-W-AGFIdentityInformation,

id-WarningAreaCoordinates,

id-WarningAreaList,

id-WarningMessageContents,

id-WarningSecurityInfo,

id-WarningType,

id-WUS-Assistance-Information,

id-XrDeviceWith2Rx,

id-SLPositioningRangingServiceInfo,

id-ExtendedOldAMF,

id-Aerial-UE-FlightInformationOngoingReporting-failed

FROM NGAP-Constants;

-- **************************************************************
--
-- PDU SESSION MANAGEMENT ELEMENTARY PROCEDURES
--
-- **************************************************************

-- **************************************************************
--
-- PDU Session Resource Setup Elementary Procedure
--
-- **************************************************************

-- **************************************************************
--
-- PDU SESSION RESOURCE SETUP REQUEST

--
-- **************************************************************

PDUSessionResourceSetupRequest ::= SEQUENCE {

protocolIEs
ProtocolIE-Container

{ {PDUSessionResourceSetupRequestIEs} },

...
}

PDUSessionResourceSetupRequestIEs NGAP-PROTOCOL-IES ::= {

{ ID id-AMF-UE-NGAP-ID

CRITICALITY reject TYPE AMF-UE-NGAP-ID

PRESENCE mandatory
}|

{ ID id-RAN-UE-NGAP-ID

CRITICALITY reject TYPE RAN-UE-NGAP-ID

PRESENCE mandatory
}|

{ ID id-RANPagingPriority

CRITICALITY ignore TYPE RANPagingPriority

PRESENCE optional
}|

{ ID id-NAS-PDU

CRITICALITY reject TYPE NAS-PDU

PRESENCE optional
}|

{ ID id-PDUSessionResourceSetupListSUReq

CRITICALITY reject TYPE PDUSessionResourceSetupListSUReq
PRESENCE mandatory
}|

{ ID id-UEAggregateMaximumBitRate

CRITICALITY ignore TYPE UEAggregateMaximumBitRate

PRESENCE optional
}|

{ ID id-UESliceMaximumBitRateList

CRITICALITY ignore TYPE UESliceMaximumBitRateList

PRESENCE optional
},

...
}

-- **************************************************************
--
-- PDU SESSION RESOURCE SETUP RESPONSE
--
-- **************************************************************

PDUSessionResourceSetupResponse ::= SEQUENCE {

protocolIEs
ProtocolIE-Container

{ {PDUSessionResourceSetupResponseIEs} },

...
}

PDUSessionResourceSetupResponseIEs NGAP-PROTOCOL-IES ::= {

{ ID id-AMF-UE-NGAP-ID

CRITICALITY ignore TYPE AMF-UE-NGAP-ID

PRESENCE mandatory
}|

{ ID id-RAN-UE-NGAP-ID

CRITICALITY ignore TYPE RAN-UE-NGAP-ID

PRESENCE mandatory
}|

{ ID id-PDUSessionResourceSetupListSURes

CRITICALITY ignore TYPE PDUSessionResourceSetupListSURes

PRESENCE optional
}|

{ ID id-PDUSessionResourceFailedToSetupListSURes
CRITICALITY ignore TYPE PDUSessionResourceFailedToSetupListSURes
PRESENCE optional
}|

{ ID id-CriticalityDiagnostics

CRITICALITY ignore TYPE CriticalityDiagnostics

PRESENCE optional
}|

{ ID id-UserLocationInformation

CRITICALITY ignore TYPE UserLocationInformation

PRESENCE optional
},

...
}

-- **************************************************************
--
-- PDU Session Resource Release Elementary Procedure
--
-- **************************************************************

-- **************************************************************
--
-- PDU SESSION RESOURCE RELEASE COMMAND

--
-- **************************************************************

PDUSessionResourceReleaseCommand ::= SEQUENCE {

protocolIEs
ProtocolIE-Container

{ {PDUSessionResourceReleaseCommandIEs} },

...
}

PDUSessionResourceReleaseCommandIEs NGAP-PROTOCOL-IES ::= {

{ ID id-AMF-UE-NGAP-ID

CRITICALITY reject TYPE AMF-UE-NGAP-ID

PRESENCE mandatory
}|

{ ID id-RAN-UE-NGAP-ID

CRITICALITY reject TYPE RAN-UE-NGAP-ID

PRESENCE mandatory
}|

{ ID id-RANPagingPriority

CRITICALITY ignore TYPE RANPagingPriority

PRESENCE optional
}|

{ ID id-NAS-PDU

CRITICALITY ignore TYPE NAS-PDU

PRESENCE optional
}|

{ ID id-PDUSessionResourceToReleaseListRelCmd

CRITICALITY reject TYPE PDUSessionResourceToReleaseListRelCmd
PRESENCE mandatory
},

...
}

-- **************************************************************
--
-- PDU SESSION RESOURCE RELEASE RESPONSE
--
-- **************************************************************

PDUSessionResourceReleaseResponse ::= SEQUENCE {

protocolIEs
ProtocolIE-Container

{ {PDUSessionResourceReleaseResponseIEs} },

...
}

PDUSessionResourceReleaseResponseIEs NGAP-PROTOCOL-IES ::= {

{ ID id-AMF-UE-NGAP-ID

CRITICALITY ignore TYPE AMF-UE-NGAP-ID

PRESENCE mandatory
}|

{ ID id-RAN-UE-NGAP-ID

CRITICALITY ignore TYPE RAN-UE-NGAP-ID

PRESENCE mandatory
}|

{ ID id-PDUSessionResourceReleasedListRelRes

CRITICALITY ignore TYPE PDUSessionResourceReleasedListRelRes
PRESENCE mandatory
}|

{ ID id-UserLocationInformation

CRITICALITY ignore TYPE UserLocationInformation

PRESENCE optional
}|

{ ID id-CriticalityDiagnostics

CRITICALITY ignore TYPE CriticalityDiagnostics

PRESENCE optional
},

...
}

-- **************************************************************
--
-- PDU Session Resource Modify Elementary Procedure
--
-- **************************************************************

-- **************************************************************
--
-- PDU SESSION RESOURCE MODIFY REQUEST
--
-- **************************************************************

PDUSessionResourceModifyRequest ::= SEQUENCE {

protocolIEs
ProtocolIE-Container

{ {PDUSessionResourceModifyRequestIEs} },

...
}

PDUSessionResourceModifyRequestIEs NGAP-PROTOCOL-IES ::= {

{ ID id-AMF-UE-NGAP-ID

CRITICALITY reject TYPE AMF-UE-NGAP-ID

PRESENCE mandatory
}|

{ ID id-RAN-UE-NGAP-ID

CRITICALITY reject TYPE RAN-UE-NGAP-ID

PRESENCE mandatory
}|

{ ID id-RANPagingPriority

CRITICALITY ignore TYPE RANPagingPriority

PRESENCE optional
}|

{ ID id-PDUSessionResourceModifyListModReq
CRITICALITY reject TYPE PDUSessionResourceModifyListModReq PRESENCE mandatory
},

...
}

-- **************************************************************
--
-- PDU SESSION RESOURCE MODIFY RESPONSE
--
-- **************************************************************

PDUSessionResourceModifyResponse ::= SEQUENCE {

protocolIEs
ProtocolIE-Container

{ {PDUSessionResourceModifyResponseIEs} },

...
}

PDUSessionResourceModifyResponseIEs NGAP-PROTOCOL-IES ::= {

{ ID id-AMF-UE-NGAP-ID

CRITICALITY ignore TYPE AMF-UE-NGAP-ID

PRESENCE mandatory

}|

{ ID id-RAN-UE-NGAP-ID

CRITICALITY ignore TYPE RAN-UE-NGAP-ID

PRESENCE mandatory

}|

{ ID id-PDUSessionResourceModifyListModRes

CRITICALITY ignore TYPE PDUSessionResourceModifyListModRes

PRESENCE optional

}|

{ ID id-PDUSessionResourceFailedToModifyListModRes
CRITICALITY ignore TYPE PDUSessionResourceFailedToModifyListModRes
PRESENCE optional

}|

{ ID id-UserLocationInformation

CRITICALITY ignore TYPE UserLocationInformation

PRESENCE optional

}|

{ ID id-CriticalityDiagnostics

CRITICALITY ignore TYPE CriticalityDiagnostics

PRESENCE optional

},

...
}

-- **************************************************************
--
-- PDU Session Resource Notify Elementary Procedure
--
-- **************************************************************

-- **************************************************************
--
-- PDU SESSION RESOURCE NOTIFY
--
-- **************************************************************

PDUSessionResourceNotify ::= SEQUENCE {

protocolIEs
ProtocolIE-Container

{ {PDUSessionResourceNotifyIEs} },

...
}

PDUSessionResourceNotifyIEs NGAP-PROTOCOL-IES ::= {

{ ID id-AMF-UE-NGAP-ID

CRITICALITY reject TYPE AMF-UE-NGAP-ID

PRESENCE mandatory
}|

{ ID id-RAN-UE-NGAP-ID

CRITICALITY reject TYPE RAN-UE-NGAP-ID

PRESENCE mandatory
}|

{ ID id-PDUSessionResourceNotifyList

CRITICALITY reject TYPE PDUSessionResourceNotifyList

PRESENCE optional
}|

{ ID id-PDUSessionResourceReleasedListNot

CRITICALITY ignore TYPE PDUSessionResourceReleasedListNot

PRESENCE optional
}|

{ ID id-UserLocationInformation

CRITICALITY ignore TYPE UserLocationInformation

PRESENCE optional
},

...
}

-- **************************************************************
--
-- PDU Session Resource Modify Indication Elementary Procedure
--
-- **************************************************************

-- **************************************************************
--
-- PDU SESSION RESOURCE MODIFY INDICATION
--
-- **************************************************************

PDUSessionResourceModifyIndication ::= SEQUENCE {

protocolIEs
ProtocolIE-Container

{ {PDUSessionResourceModifyIndicationIEs} },

...
}

PDUSessionResourceModifyIndicationIEs NGAP-PROTOCOL-IES ::= {

{ ID id-AMF-UE-NGAP-ID

CRITICALITY reject TYPE AMF-UE-NGAP-ID

PRESENCE mandatory
}|

{ ID id-RAN-UE-NGAP-ID

CRITICALITY reject TYPE RAN-UE-NGAP-ID

PRESENCE mandatory
}|

{ ID id-PDUSessionResourceModifyListModInd
CRITICALITY reject TYPE PDUSessionResourceModifyListModInd
PRESENCE mandatory
}|

{ ID id-UserLocationInformation

CRITICALITY ignore TYPE UserLocationInformation

PRESENCE optional
},

...
}

-- **************************************************************
--
-- PDU SESSION RESOURCE MODIFY CONFIRM
--
-- **************************************************************

PDUSessionResourceModifyConfirm ::= SEQUENCE {

protocolIEs
ProtocolIE-Container

{ {PDUSessionResourceModifyConfirmIEs} },

...
}

PDUSessionResourceModifyConfirmIEs NGAP-PROTOCOL-IES ::= {

{ ID id-AMF-UE-NGAP-ID

CRITICALITY ignore TYPE AMF-UE-NGAP-ID

PRESENCE mandatory
}|

{ ID id-RAN-UE-NGAP-ID

CRITICALITY ignore TYPE RAN-UE-NGAP-ID

PRESENCE mandatory
}|

{ ID id-PDUSessionResourceModifyListModCfm

CRITICALITY ignore TYPE PDUSessionResourceModifyListModCfm
PRESENCE optional }|

{ ID id-PDUSessionResourceFailedToModifyListModCfm CRITICALITY ignore TYPE PDUSessionResourceFailedToModifyListModCfm
PRESENCE optional }|

{ ID id-CriticalityDiagnostics

CRITICALITY ignore TYPE CriticalityDiagnostics

PRESENCE optional
},

...
}

-- **************************************************************
--
-- UE CONTEXT MANAGEMENT ELEMENTARY PROCEDURES
--
-- **************************************************************

-- **************************************************************
--
-- Initial Context Setup Elementary Procedure
--
-- **************************************************************

-- **************************************************************
--
-- INITIAL CONTEXT SETUP REQUEST
--
-- **************************************************************

InitialContextSetupRequest ::= SEQUENCE {

protocolIEs
ProtocolIE-Container

{ {InitialContextSetupRequestIEs} },

...
}

InitialContextSetupRequestIEs NGAP-PROTOCOL-IES ::= {

{ ID id-AMF-UE-NGAP-ID

CRITICALITY reject TYPE AMF-UE-NGAP-ID

PRESENCE mandatory
}|

{ ID id-RAN-UE-NGAP-ID

CRITICALITY reject TYPE RAN-UE-NGAP-ID

PRESENCE mandatory
}|

{ ID id-OldAMF

CRITICALITY reject TYPE AMFName

PRESENCE optional
}|

{ ID id-UEAggregateMaximumBitRate

CRITICALITY reject TYPE UEAggregateMaximumBitRate

PRESENCE conditional }|
-- The above IE shall be present if the PDU Session Resource Setup List IE is present

{ ID id-CoreNetworkAssistanceInformationForInactive
CRITICALITY ignore TYPE CoreNetworkAssistanceInformationForInactive
PRESENCE
optional

}|

{ ID id-GUAMI

CRITICALITY reject TYPE GUAMI

PRESENCE mandatory
}|

{ ID id-PDUSessionResourceSetupListCxtReq

CRITICALITY reject TYPE PDUSessionResourceSetupListCxtReq

PRESENCE optional
}|

{ ID id-AllowedNSSAI

CRITICALITY reject TYPE AllowedNSSAI

PRESENCE mandatory
}|

{ ID id-UESecurityCapabilities

CRITICALITY reject TYPE UESecurityCapabilities

PRESENCE mandatory
}|

{ ID id-SecurityKey

CRITICALITY reject TYPE SecurityKey

PRESENCE mandatory
}|

{ ID id-TraceActivation

CRITICALITY ignore TYPE TraceActivation

PRESENCE optional
}|

{ ID id-MobilityRestrictionList

CRITICALITY ignore TYPE MobilityRestrictionList

PRESENCE optional
}|

{ ID id-UERadioCapability

CRITICALITY ignore TYPE UERadioCapability

PRESENCE optional
}|

{ ID id-IndexToRFSP

CRITICALITY ignore TYPE IndexToRFSP

PRESENCE optional
}|

{ ID id-MaskedIMEISV

CRITICALITY ignore TYPE MaskedIMEISV

PRESENCE optional
}|

{ ID id-NAS-PDU

CRITICALITY ignore TYPE NAS-PDU

PRESENCE optional
}|

{ ID id-EmergencyFallbackIndicator

CRITICALITY reject TYPE EmergencyFallbackIndicator

PRESENCE optional
}|

{ ID id-RRCInactiveTransitionReportRequest
CRITICALITY ignore TYPE RRCInactiveTransitionReportRequest

PRESENCE optional
}|

{ ID id-UERadioCapabilityForPaging

CRITICALITY ignore TYPE UERadioCapabilityForPaging

PRESENCE optional
}|

{ ID id-RedirectionVoiceFallback

CRITICALITY ignore TYPE RedirectionVoiceFallback

PRESENCE optional
}|

{ ID id-LocationReportingRequestType

CRITICALITY ignore TYPE LocationReportingRequestType

PRESENCE optional
}|

{ ID id-CNAssistedRANTuning

CRITICALITY ignore TYPE CNAssistedRANTuning

PRESENCE optional
}|

{ ID id-SRVCCOperationPossible

CRITICALITY ignore TYPE SRVCCOperationPossible

PRESENCE optional
}|

{ ID id-IAB-Authorized

CRITICALITY ignore TYPE IAB-Authorized

PRESENCE optional
}|

{ ID id-Enhanced-CoverageRestriction

CRITICALITY ignore TYPE Enhanced-CoverageRestriction

PRESENCE optional
}|

{ ID id-Extended-ConnectedTime

CRITICALITY ignore TYPE Extended-ConnectedTime

PRESENCE optional
}|

{ ID id-UE-DifferentiationInfo

CRITICALITY ignore TYPE UE-DifferentiationInfo

PRESENCE optional
}|

{ ID id-NRV2XServicesAuthorized

CRITICALITY ignore TYPE NRV2XServicesAuthorized

PRESENCE optional
}|

{ ID id-LTEV2XServicesAuthorized

CRITICALITY ignore TYPE LTEV2XServicesAuthorized

PRESENCE optional
}|

{ ID id-NRUESidelinkAggregateMaximumBitrate
CRITICALITY ignore TYPE NRUESidelinkAggregateMaximumBitrate

PRESENCE optional
}|

{ ID id-LTEUESidelinkAggregateMaximumBitrate
CRITICALITY ignore TYPE LTEUESidelinkAggregateMaximumBitrate

PRESENCE optional
}|

{ ID id-PC5QoSParameters

CRITICALITY ignore TYPE PC5QoSParameters

PRESENCE optional
}|

{ ID id-CEmodeBrestricted

CRITICALITY ignore TYPE CEmodeBrestricted

PRESENCE optional
}|

{ ID id-UE-UP-CIoT-Support

CRITICALITY ignore TYPE UE-UP-CIoT-Support

PRESENCE optional
}|

{ ID id-RGLevelWirelineAccessCharacteristics
CRITICALITY ignore TYPE RGLevelWirelineAccessCharacteristics

PRESENCE optional
}|

{ ID id-ManagementBasedMDTPLMNList

CRITICALITY ignore TYPE MDTPLMNList

PRESENCE optional
}|

{ ID id-UERadioCapabilityID

CRITICALITY reject TYPE UERadioCapabilityID

PRESENCE optional
}|

{ ID id-TimeSyncAssistanceInfo

CRITICALITY ignore TYPE TimeSyncAssistanceInfo

PRESENCE optional
}|

{ ID id-QMCConfigInfo

CRITICALITY ignore TYPE QMCConfigInfo

PRESENCE optional
}|

{ ID id-TargetNSSAIInformation

CRITICALITY ignore TYPE TargetNSSAIInformation

PRESENCE optional
}|

{ ID id-UESliceMaximumBitRateList

CRITICALITY ignore TYPE UESliceMaximumBitRateList

PRESENCE optional
}|

{ ID id-FiveG-ProSeAuthorized

CRITICALITY ignore TYPE FiveG-ProSeAuthorized

PRESENCE optional
}|

{ ID id-FiveG-ProSeUEPC5AggregateMaximumBitRate CRITICALITY ignore TYPE NRUESidelinkAggregateMaximumBitrate

PRESENCE optional
}|

{ ID id-FiveG-ProSePC5QoSParameters

CRITICALITY ignore TYPE FiveG-ProSePC5QoSParameters

PRESENCE optional
}|

{ ID id-NetworkControlledRepeaterAuthorized
CRITICALITY ignore TYPE NetworkControlledRepeaterAuthorized

PRESENCE optional
}|

{ ID id-AerialUEsubscriptionInformation

CRITICALITY ignore TYPE AerialUEsubscriptionInformation

PRESENCE optional
}|

{ ID id-NR-A2X-ServicesAuthorized

CRITICALITY ignore TYPE NR-A2X-ServicesAuthorized

PRESENCE optional
}|

{ ID id-LTE-A2X-ServicesAuthorized

CRITICALITY ignore TYPE LTE-A2X-ServicesAuthorized

PRESENCE optional
}|

{ ID id-NR-A2X-UE-PC5-AggregateMaximumBitRate
CRITICALITY ignore TYPE NRUESidelinkAggregateMaximumBitrate

PRESENCE optional
}|

{ ID id-LTE-A2X-UE-PC5-AggregateMaximumBitRate CRITICALITY ignore TYPE LTEUESidelinkAggregateMaximumBitrate

PRESENCE optional
}|

{ ID id-A2X-PC5-QoS-Parameters

CRITICALITY ignore TYPE A2X-PC5-QoS-Parameters

PRESENCE optional
}|

{ ID id-MobileIAB-Authorized

CRITICALITY ignore TYPE MobileIAB-Authorized

PRESENCE optional
}|

{ ID id-Partially-Allowed-NSSAI

CRITICALITY ignore TYPE Partially-Allowed-NSSAI

PRESENCE optional
}|

{ ID id-SLPositioningRangingServiceInfo

CRITICALITY ignore TYPE SLPositioningRangingServiceInfo

PRESENCE optional
}|

{ ID id-ExtendedOldAMF

CRITICALITY ignore TYPE Extended-AMFName

PRESENCE optional
}|

{ ID id-AMF-UE-NGAP-ID2

CRITICALITY ignore TYPE AMF-UE-NGAP-ID

PRESENCE optional
},

...
}

-- **************************************************************
--
-- INITIAL CONTEXT SETUP RESPONSE
--
-- **************************************************************

InitialContextSetupResponse ::= SEQUENCE {

protocolIEs
ProtocolIE-Container

{ {InitialContextSetupResponseIEs} },

...
}

InitialContextSetupResponseIEs NGAP-PROTOCOL-IES ::= {

{ ID id-AMF-UE-NGAP-ID

CRITICALITY ignore TYPE AMF-UE-NGAP-ID

PRESENCE mandatory

}|

{ ID id-RAN-UE-NGAP-ID

CRITICALITY ignore TYPE RAN-UE-NGAP-ID

PRESENCE mandatory

}|

{ ID id-PDUSessionResourceSetupListCxtRes

CRITICALITY ignore TYPE PDUSessionResourceSetupListCxtRes

PRESENCE optional

}|

{ ID id-PDUSessionResourceFailedToSetupListCxtRes
CRITICALITY ignore TYPE PDUSessionResourceFailedToSetupListCxtRes
PRESENCE optional

}|

{ ID id-CriticalityDiagnostics

CRITICALITY ignore TYPE CriticalityDiagnostics

PRESENCE optional

},

...

}

-- **************************************************************
--
-- INITIAL CONTEXT SETUP FAILURE
--
-- **************************************************************

InitialContextSetupFailure ::= SEQUENCE {

protocolIEs
ProtocolIE-Container

{ {InitialContextSetupFailureIEs} },

...
}

InitialContextSetupFailureIEs NGAP-PROTOCOL-IES ::= {

{ ID id-AMF-UE-NGAP-ID

CRITICALITY ignore TYPE AMF-UE-NGAP-ID

PRESENCE mandatory

}|

{ ID id-RAN-UE-NGAP-ID

CRITICALITY ignore TYPE RAN-UE-NGAP-ID

PRESENCE mandatory

}|

{ ID id-PDUSessionResourceFailedToSetupListCxtFail CRITICALITY ignore TYPE PDUSessionResourceFailedToSetupListCxtFail
PRESENCE optional

}|

{ ID id-Cause

CRITICALITY ignore TYPE Cause

PRESENCE mandatory

}|

{ ID id-CriticalityDiagnostics

CRITICALITY ignore TYPE CriticalityDiagnostics

PRESENCE optional

},

...
}

-- **************************************************************
--
-- UE Context Release Request Elementary Procedure
--
-- **************************************************************

-- **************************************************************
--
-- UE CONTEXT RELEASE REQUEST
--
-- **************************************************************

UEContextReleaseRequest ::= SEQUENCE {

protocolIEs
ProtocolIE-Container

{ {UEContextReleaseRequest-IEs} },

...
}

UEContextReleaseRequest-IEs NGAP-PROTOCOL-IES ::= {

{ ID id-AMF-UE-NGAP-ID

CRITICALITY reject TYPE AMF-UE-NGAP-ID

PRESENCE mandatory
}|

{ ID id-RAN-UE-NGAP-ID

CRITICALITY reject TYPE RAN-UE-NGAP-ID

PRESENCE mandatory
}|

{ ID id-PDUSessionResourceListCxtRelReq
CRITICALITY reject TYPE PDUSessionResourceListCxtRelReq

PRESENCE optional
}|

{ ID id-Cause

CRITICALITY ignore TYPE Cause

PRESENCE mandatory
}|

{ ID id-GW-Context-Release-Indication

CRITICALITY reject TYPE GW-Context-Release-Indication

PRESENCE optional
},

...
}

-- **************************************************************
--
-- UE Context Release Elementary Procedure
--
-- **************************************************************

-- **************************************************************
--
-- UE CONTEXT RELEASE COMMAND
--
-- **************************************************************

UEContextReleaseCommand ::= SEQUENCE {

protocolIEs
ProtocolIE-Container

{ {UEContextReleaseCommand-IEs} },

...
}

UEContextReleaseCommand-IEs NGAP-PROTOCOL-IES ::= {

{ ID id-UE-NGAP-IDs

CRITICALITY reject TYPE UE-NGAP-IDs

PRESENCE mandatory }|

{ ID id-Cause

CRITICALITY ignore TYPE Cause

PRESENCE mandatory },

...
}

-- **************************************************************
--
-- UE CONTEXT RELEASE COMPLETE
--
-- **************************************************************

UEContextReleaseComplete ::= SEQUENCE {

protocolIEs
ProtocolIE-Container

{ {UEContextReleaseComplete-IEs} },

...
}

UEContextReleaseComplete-IEs NGAP-PROTOCOL-IES ::= {

{ ID id-AMF-UE-NGAP-ID

CRITICALITY ignore TYPE AMF-UE-NGAP-ID

PRESENCE mandatory
}|

{ ID id-RAN-UE-NGAP-ID

CRITICALITY ignore TYPE RAN-UE-NGAP-ID

PRESENCE mandatory
}|

{ ID id-UserLocationInformation

CRITICALITY ignore TYPE UserLocationInformation

PRESENCE optional
}|

{ ID id-InfoOnRecommendedCellsAndRANNodesForPaging CRITICALITY ignore TYPE InfoOnRecommendedCellsAndRANNodesForPaging PRESENCE optional
}|

{ ID id-PDUSessionResourceListCxtRelCpl

CRITICALITY reject TYPE PDUSessionResourceListCxtRelCpl

PRESENCE optional
}|

{ ID id-CriticalityDiagnostics

CRITICALITY ignore TYPE CriticalityDiagnostics

PRESENCE optional
}|

{ ID id-PagingAssisDataforCEcapabUE

CRITICALITY ignore TYPE PagingAssisDataforCEcapabUE

PRESENCE optional
},

...
}

-- **************************************************************
--
-- UE Context Resume Elementary Procedure
--
-- **************************************************************

-- **************************************************************
--
-- UE CONTEXT RESUME REQUEST

--
-- **************************************************************

UEContextResumeRequest ::= SEQUENCE {

protocolIEs
ProtocolIE-Container

{ {UEContextResumeRequestIEs} },

...
}

UEContextResumeRequestIEs NGAP-PROTOCOL-IES ::= {

{ ID id-AMF-UE-NGAP-ID

CRITICALITY reject TYPE AMF-UE-NGAP-ID

PRESENCE mandatory
}|

{ ID id-RAN-UE-NGAP-ID

CRITICALITY reject TYPE RAN-UE-NGAP-ID

PRESENCE mandatory
}|

{ ID id-RRC-Resume-Cause

CRITICALITY ignore TYPE RRCEstablishmentCause

PRESENCE mandatory
}|

{ ID id-PDUSessionResourceResumeListRESReq
CRITICALITY reject TYPE PDUSessionResourceResumeListRESReq

PRESENCE optional
}|

{ ID id-PDUSessionResourceFailedToResumeListRESReq
CRITICALITY reject TYPE PDUSessionResourceFailedToResumeListRESReq

PRESENCE
optional

}|

{ ID id-Suspend-Request-Indication

CRITICALITY ignore TYPE Suspend-Request-Indication

PRESENCE optional
}|

{ ID id-InfoOnRecommendedCellsAndRANNodesForPaging CRITICALITY ignore TYPE InfoOnRecommendedCellsAndRANNodesForPaging
PRESENCE optional

}|

{ ID id-PagingAssisDataforCEcapabUE

CRITICALITY ignore TYPE PagingAssisDataforCEcapabUE

PRESENCE optional
}|

{ ID id-UserLocationInformation

CRITICALITY ignore TYPE UserLocationInformation

PRESENCE optional
},

...
}

-- **************************************************************
--
-- UE CONTEXT RESUME RESPONSE
--
-- **************************************************************

UEContextResumeResponse ::= SEQUENCE {

protocolIEs
ProtocolIE-Container

{ {UEContextResumeResponseIEs} },

...
}

UEContextResumeResponseIEs NGAP-PROTOCOL-IES ::= {

{ ID id-AMF-UE-NGAP-ID

CRITICALITY ignore TYPE AMF-UE-NGAP-ID

PRESENCE mandatory
}|

{ ID id-RAN-UE-NGAP-ID

CRITICALITY ignore TYPE RAN-UE-NGAP-ID

PRESENCE mandatory
}|

{ ID id-PDUSessionResourceResumeListRESRes
CRITICALITY reject TYPE PDUSessionResourceResumeListRESRes

PRESENCE optional
}|

{ ID id-PDUSessionResourceFailedToResumeListRESRes
CRITICALITY reject TYPE PDUSessionResourceFailedToResumeListRESRes

PRESENCE
optional

}|

{ ID id-SecurityContext

CRITICALITY reject TYPE SecurityContext

PRESENCE optional
}|

{ ID id-Suspend-Response-Indication

CRITICALITY ignore TYPE Suspend-Response-Indication

PRESENCE optional
}|

{ ID id-Extended-ConnectedTime

CRITICALITY ignore TYPE Extended-ConnectedTime

PRESENCE optional
}|

{ ID id-CriticalityDiagnostics

CRITICALITY ignore TYPE CriticalityDiagnostics

PRESENCE optional
},

...
}

-- **************************************************************
--
-- UE CONTEXT RESUME FAILURE
--
-- **************************************************************

UEContextResumeFailure ::= SEQUENCE {

protocolIEs
ProtocolIE-Container

{ { UEContextResumeFailureIEs} },

...
}

UEContextResumeFailureIEs NGAP-PROTOCOL-IES ::= {

{ ID id-AMF-UE-NGAP-ID

CRITICALITY ignore TYPE AMF-UE-NGAP-ID

PRESENCE mandatory
}|

{ ID id-RAN-UE-NGAP-ID

CRITICALITY ignore TYPE RAN-UE-NGAP-ID

PRESENCE mandatory
}|

{ ID id-Cause

CRITICALITY ignore TYPE Cause

PRESENCE mandatory
}|

{ ID id-CriticalityDiagnostics
CRITICALITY ignore TYPE CriticalityDiagnostics
PRESENCE optional
},

...
}

-- **************************************************************
--
-- UE Context Suspend Elementary Procedure
--
-- **************************************************************

-- **************************************************************
--
-- UE CONTEXT SUSPEND REQUEST
--
-- **************************************************************

UEContextSuspendRequest ::= SEQUENCE {

protocolIEs
ProtocolIE-Container

{ {UEContextSuspendRequestIEs} },

...
}

UEContextSuspendRequestIEs NGAP-PROTOCOL-IES ::= {

{ ID id-AMF-UE-NGAP-ID

CRITICALITY reject TYPE AMF-UE-NGAP-ID

PRESENCE mandatory

}|

{ ID id-RAN-UE-NGAP-ID

CRITICALITY reject TYPE RAN-UE-NGAP-ID

PRESENCE mandatory

}|

{ ID id-InfoOnRecommendedCellsAndRANNodesForPaging CRITICALITY ignore TYPE InfoOnRecommendedCellsAndRANNodesForPaging
PRESENCE optional

}|

{ ID id-PagingAssisDataforCEcapabUE

CRITICALITY ignore TYPE PagingAssisDataforCEcapabUE

PRESENCE optional

}|

{ ID id-PDUSessionResourceSuspendListSUSReq

CRITICALITY reject TYPE PDUSessionResourceSuspendListSUSReq

PRESENCE optional

}|

{ ID id-UserLocationInformation

CRITICALITY ignore TYPE UserLocationInformation

PRESENCE optional

},

...
}

-- **************************************************************
--
-- UE CONTEXT SUSPEND RESPONSE
--
-- **************************************************************

UEContextSuspendResponse ::= SEQUENCE {

protocolIEs
ProtocolIE-Container

{ {UEContextSuspendResponseIEs} },

...
}

UEContextSuspendResponseIEs NGAP-PROTOCOL-IES ::= {

{ ID id-AMF-UE-NGAP-ID

CRITICALITY ignore TYPE AMF-UE-NGAP-ID

PRESENCE mandatory
}|

{ ID id-RAN-UE-NGAP-ID

CRITICALITY ignore TYPE RAN-UE-NGAP-ID

PRESENCE mandatory
}|

{ ID id-SecurityContext

CRITICALITY reject TYPE SecurityContext

PRESENCE optional
}|

{ ID id-CriticalityDiagnostics

CRITICALITY ignore TYPE CriticalityDiagnostics

PRESENCE optional
},

...
}

-- **************************************************************
--
-- UE CONTEXT SUSPEND FAILURE
--
-- **************************************************************

UEContextSuspendFailure ::= SEQUENCE {

protocolIEs
ProtocolIE-Container

{ { UEContextSuspendFailureIEs} },

...
}

UEContextSuspendFailureIEs NGAP-PROTOCOL-IES ::= {

{ ID id-AMF-UE-NGAP-ID

CRITICALITY ignore TYPE AMF-UE-NGAP-ID

PRESENCE mandatory
}|

{ ID id-RAN-UE-NGAP-ID

CRITICALITY ignore TYPE RAN-UE-NGAP-ID

PRESENCE mandatory
}|

{ ID id-Cause

CRITICALITY ignore TYPE Cause

PRESENCE mandatory
}|

{ ID id-CriticalityDiagnostics
CRITICALITY ignore TYPE CriticalityDiagnostics
PRESENCE optional
},

...
}

-- **************************************************************
--
-- UE Context Modification Elementary Procedure
--
-- **************************************************************

-- **************************************************************
--
-- UE CONTEXT MODIFICATION REQUEST
--
-- **************************************************************

UEContextModificationRequest ::= SEQUENCE {

protocolIEs
ProtocolIE-Container

{ {UEContextModificationRequestIEs} },

...
}

UEContextModificationRequestIEs NGAP-PROTOCOL-IES ::= {

{ ID id-AMF-UE-NGAP-ID

CRITICALITY reject TYPE AMF-UE-NGAP-ID

PRESENCE mandatory
}|

{ ID id-RAN-UE-NGAP-ID

CRITICALITY reject TYPE RAN-UE-NGAP-ID

PRESENCE mandatory
}|

{ ID id-RANPagingPriority

CRITICALITY ignore TYPE RANPagingPriority

PRESENCE optional
}|

{ ID id-SecurityKey

CRITICALITY reject TYPE SecurityKey

PRESENCE optional
}|

{ ID id-IndexToRFSP

CRITICALITY ignore TYPE IndexToRFSP

PRESENCE optional
}|

{ ID id-UEAggregateMaximumBitRate

CRITICALITY ignore TYPE UEAggregateMaximumBitRate

PRESENCE optional
}|

{ ID id-UESecurityCapabilities

CRITICALITY reject TYPE UESecurityCapabilities

PRESENCE optional
}|

{ ID id-CoreNetworkAssistanceInformationForInactive
CRITICALITY ignore TYPE CoreNetworkAssistanceInformationForInactive
PRESENCE
optional

}|

{ ID id-EmergencyFallbackIndicator

CRITICALITY reject TYPE EmergencyFallbackIndicator

PRESENCE optional
}|

{ ID id-NewAMF-UE-NGAP-ID

CRITICALITY reject TYPE AMF-UE-NGAP-ID

PRESENCE optional
}|

{ ID id-RRCInactiveTransitionReportRequest
CRITICALITY ignore TYPE RRCInactiveTransitionReportRequest
PRESENCE optional
}|

{ ID id-NewGUAMI

CRITICALITY reject TYPE GUAMI

PRESENCE optional
}|

{ ID id-CNAssistedRANTuning

CRITICALITY ignore TYPE CNAssistedRANTuning

PRESENCE optional
}|

{ ID id-SRVCCOperationPossible

CRITICALITY ignore TYPE SRVCCOperationPossible

PRESENCE optional
}|

{ ID id-IAB-Authorized

CRITICALITY ignore TYPE IAB-Authorized

PRESENCE optional
}|

{ ID id-NRV2XServicesAuthorized

CRITICALITY ignore TYPE NRV2XServicesAuthorized

PRESENCE optional
}|

{ ID id-LTEV2XServicesAuthorized

CRITICALITY ignore TYPE LTEV2XServicesAuthorized

PRESENCE optional
}|

{ ID id-NRUESidelinkAggregateMaximumBitrate
CRITICALITY ignore TYPE NRUESidelinkAggregateMaximumBitrate
PRESENCE optional
}|

{ ID id-LTEUESidelinkAggregateMaximumBitrate
CRITICALITY ignore TYPE LTEUESidelinkAggregateMaximumBitrate
PRESENCE optional
}|

{ ID id-PC5QoSParameters

CRITICALITY ignore TYPE PC5QoSParameters

PRESENCE optional
}|

{ ID id-UERadioCapabilityID

CRITICALITY reject TYPE UERadioCapabilityID

PRESENCE optional
}|

{ ID id-RGLevelWirelineAccessCharacteristics
CRITICALITY ignore TYPE RGLevelWirelineAccessCharacteristics
PRESENCE optional
}|

{ ID id-TimeSyncAssistanceInfo

CRITICALITY ignore TYPE TimeSyncAssistanceInfo

PRESENCE optional
}|

{ ID id-QMCConfigInfo

CRITICALITY ignore TYPE QMCConfigInfo

PRESENCE optional
}|

{ ID id-QMCDeactivation

CRITICALITY ignore TYPE QMCDeactivation

PRESENCE optional
}|

{ ID id-UESliceMaximumBitRateList

CRITICALITY ignore TYPE UESliceMaximumBitRateList

PRESENCE optional
}|

{ ID id-ManagementBasedMDTPLMNModificationList CRITICALITY ignore TYPE MDTPLMNModificationList

PRESENCE optional
}|

{ ID id-FiveG-ProSeAuthorized

CRITICALITY ignore TYPE FiveG-ProSeAuthorized

PRESENCE optional
}|

{ ID id-FiveG-ProSeUEPC5AggregateMaximumBitRate CRITICALITY ignore TYPE NRUESidelinkAggregateMaximumBitrate
PRESENCE optional
}|

{ ID id-FiveG-ProSePC5QoSParameters

CRITICALITY ignore TYPE FiveG-ProSePC5QoSParameters

PRESENCE optional
}|

{ ID id-NetworkControlledRepeaterAuthorized
CRITICALITY ignore TYPE NetworkControlledRepeaterAuthorized
PRESENCE optional
}|

{ ID id-AerialUEsubscriptionInformation

CRITICALITY ignore TYPE AerialUEsubscriptionInformation

PRESENCE optional
}|

{ ID id-NR-A2X-ServicesAuthorized

CRITICALITY ignore TYPE NR-A2X-ServicesAuthorized

PRESENCE optional
}|

{ ID id-LTE-A2X-ServicesAuthorized

CRITICALITY ignore TYPE LTE-A2X-ServicesAuthorized

PRESENCE optional
}|

{ ID id-NR-A2X-UE-PC5-AggregateMaximumBitRate
CRITICALITY ignore TYPE NRUESidelinkAggregateMaximumBitrate
PRESENCE optional
}|

{ ID id-LTE-A2X-UE-PC5-AggregateMaximumBitRate CRITICALITY ignore TYPE LTEUESidelinkAggregateMaximumBitrate
PRESENCE optional
}|

{ ID id-A2X-PC5-QoS-Parameters

CRITICALITY ignore TYPE A2X-PC5-QoS-Parameters

PRESENCE optional
}|

{ ID id-MobileIAB-Authorized

CRITICALITY ignore TYPE MobileIAB-Authorized

PRESENCE optional
}|

{ ID id-SLPositioningRangingServiceInfo

CRITICALITY ignore TYPE SLPositioningRangingServiceInfo

PRESENCE optional
},

...
}

-- **************************************************************
--
-- UE CONTEXT MODIFICATION RESPONSE
--
-- **************************************************************

UEContextModificationResponse ::= SEQUENCE {

protocolIEs
ProtocolIE-Container

{ {UEContextModificationResponseIEs} },

...
}

UEContextModificationResponseIEs NGAP-PROTOCOL-IES ::= {

{ ID id-AMF-UE-NGAP-ID

CRITICALITY ignore TYPE AMF-UE-NGAP-ID

PRESENCE mandatory
}|

{ ID id-RAN-UE-NGAP-ID

CRITICALITY ignore TYPE RAN-UE-NGAP-ID

PRESENCE mandatory
}|

{ ID id-RRCState

CRITICALITY ignore TYPE RRCState

PRESENCE optional
}|

{ ID id-UserLocationInformation
CRITICALITY ignore TYPE UserLocationInformation
PRESENCE optional
}|

{ ID id-CriticalityDiagnostics
CRITICALITY ignore TYPE CriticalityDiagnostics
PRESENCE optional
},

...
}

-- **************************************************************
--
-- UE CONTEXT MODIFICATION FAILURE
--
-- **************************************************************

UEContextModificationFailure ::= SEQUENCE {

protocolIEs
ProtocolIE-Container

{ {UEContextModificationFailureIEs} },

...
}

UEContextModificationFailureIEs NGAP-PROTOCOL-IES ::= {

{ ID id-AMF-UE-NGAP-ID

CRITICALITY ignore TYPE AMF-UE-NGAP-ID

PRESENCE mandatory
}|

{ ID id-RAN-UE-NGAP-ID

CRITICALITY ignore TYPE RAN-UE-NGAP-ID

PRESENCE mandatory
}|

{ ID id-Cause

CRITICALITY ignore TYPE Cause

PRESENCE mandatory
}|

{ ID id-CriticalityDiagnostics
CRITICALITY ignore TYPE CriticalityDiagnostics
PRESENCE optional
},

...
}

-- **************************************************************
--
-- RRC INACTIVE TRANSITION REPORT
--
-- **************************************************************

RRCInactiveTransitionReport ::= SEQUENCE {

protocolIEs
ProtocolIE-Container

{ {RRCInactiveTransitionReportIEs} },

...
}

RRCInactiveTransitionReportIEs NGAP-PROTOCOL-IES ::= {

{ ID id-AMF-UE-NGAP-ID

CRITICALITY reject TYPE AMF-UE-NGAP-ID

PRESENCE mandatory }|

{ ID id-RAN-UE-NGAP-ID

CRITICALITY reject TYPE RAN-UE-NGAP-ID

PRESENCE mandatory }|

{ ID id-RRCState

CRITICALITY ignore TYPE RRCState

PRESENCE mandatory }|

{ ID id-UserLocationInformation
CRITICALITY ignore TYPE UserLocationInformation

PRESENCE mandatory },

...
}

-- **************************************************************
--
-- Retrieve UE Information
--
-- **************************************************************

RetrieveUEInformation ::= SEQUENCE {

protocolIEs

ProtocolIE-Container       { { RetrieveUEInformationIEs} },

...
}

RetrieveUEInformationIEs NGAP-PROTOCOL-IES ::= {

{ ID id-FiveG-S-TMSI

CRITICALITY reject TYPE FiveG-S-TMSI

PRESENCE mandatory },

...

}

-- **************************************************************

-- UE Information Transfer
--
-- **************************************************************

UEInformationTransfer ::= SEQUENCE {

protocolIEs

ProtocolIE-Container       { {  UEInformationTransferIEs} },

...
}

UEInformationTransferIEs NGAP-PROTOCOL-IES ::= {

{ ID id-FiveG-S-TMSI

CRITICALITY reject  TYPE FiveG-S-TMSI

PRESENCE mandatory
}|

{ ID id-NB-IoT-UEPriority

CRITICALITY ignore TYPE NB-IoT-UEPriority

PRESENCE optional
}|

{ ID id-UERadioCapability

CRITICALITY ignore TYPE UERadioCapability

PRESENCE optional
}|

{ ID id-S-NSSAI

CRITICALITY ignore TYPE S-NSSAI

PRESENCE optional
}|

{ ID id-AllowedNSSAI

CRITICALITY ignore TYPE AllowedNSSAI

PRESENCE optional
}|

{ ID id-UE-DifferentiationInfo
CRITICALITY ignore TYPE UE-DifferentiationInfo
PRESENCE optional
}|

{ ID id-MaskedIMEISV

CRITICALITY ignore TYPE MaskedIMEISV

PRESENCE optional
}|

{ ID id-Partially-Allowed-NSSAI
CRITICALITY ignore TYPE Partially-Allowed-NSSAI
PRESENCE optional
},

...
}

-- **************************************************************
--
-- RAN CP Relocation Indication
--
-- **************************************************************

RANCPRelocationIndication ::= SEQUENCE {

protocolIEs

ProtocolIE-Container { { RANCPRelocationIndicationIEs} },

...
}

RANCPRelocationIndicationIEs NGAP-PROTOCOL-IES ::= {

{ ID id-RAN-UE-NGAP-ID

CRITICALITY reject TYPE RAN-UE-NGAP-ID

 PRESENCE mandatory
}|

{ ID id-FiveG-S-TMSI

CRITICALITY reject TYPE FiveG-S-TMSI

 PRESENCE mandatory
}|

{ ID id-EUTRA-CGI

CRITICALITY ignore TYPE EUTRA-CGI

 PRESENCE mandatory
}|

{ ID id-TAI

CRITICALITY ignore TYPE TAI

 PRESENCE mandatory
}|

{ ID id-UL-CP-SecurityInformation

CRITICALITY reject TYPE UL-CP-SecurityInformation  PRESENCE mandatory
},

...
}

-- **************************************************************
--
-- UE MOBILITY MANAGEMENT ELEMENTARY PROCEDURES
--
-- **************************************************************

-- **************************************************************

--
-- Handover Preparation Elementary Procedure
--
-- **************************************************************

-- **************************************************************
--
-- HANDOVER REQUIRED
--
-- **************************************************************

HandoverRequired ::= SEQUENCE {

protocolIEs
ProtocolIE-Container

{ {HandoverRequiredIEs} },

...
}

HandoverRequiredIEs NGAP-PROTOCOL-IES ::= {

{ ID id-AMF-UE-NGAP-ID

CRITICALITY reject TYPE AMF-UE-NGAP-ID

PRESENCE mandatory
}|

{ ID id-RAN-UE-NGAP-ID

CRITICALITY reject TYPE RAN-UE-NGAP-ID

PRESENCE mandatory
}|

{ ID id-HandoverType

CRITICALITY reject TYPE HandoverType

PRESENCE mandatory
}|

{ ID id-Cause

CRITICALITY ignore TYPE Cause

PRESENCE mandatory
}|

{ ID id-TargetID

CRITICALITY reject TYPE TargetID

PRESENCE mandatory
}|

{ ID id-DirectForwardingPathAvailability

CRITICALITY ignore TYPE DirectForwardingPathAvailability

PRESENCE optional
}|

{ ID id-PDUSessionResourceListHORqd

CRITICALITY reject TYPE PDUSessionResourceListHORqd

PRESENCE mandatory
}|

{ ID id-SourceToTarget-TransparentContainer
CRITICALITY reject TYPE SourceToTarget-TransparentContainer
PRESENCE mandatory
},

...
}

-- **************************************************************
--
-- HANDOVER COMMAND
--
-- **************************************************************

HandoverCommand ::= SEQUENCE {

protocolIEs
ProtocolIE-Container

{ {HandoverCommandIEs} },

...
}

HandoverCommandIEs NGAP-PROTOCOL-IES ::= {

{ ID id-AMF-UE-NGAP-ID

CRITICALITY reject TYPE AMF-UE-NGAP-ID

PRESENCE mandatory
}|

{ ID id-RAN-UE-NGAP-ID

CRITICALITY reject TYPE RAN-UE-NGAP-ID

PRESENCE mandatory
}|

{ ID id-HandoverType

CRITICALITY reject TYPE HandoverType

PRESENCE mandatory
}|

{ ID id-NASSecurityParametersFromNGRAN

CRITICALITY reject TYPE NASSecurityParametersFromNGRAN

PRESENCE conditional }|
-- The above IE shall be present if the HandoverType IE is set to the value "5GStoEPPS" or "5GStoUTRAN"

{ ID id-PDUSessionResourceHandoverList

CRITICALITY ignore TYPE PDUSessionResourceHandoverList

PRESENCE optional
}|

{ ID id-PDUSessionResourceToReleaseListHOCmd

CRITICALITY ignore TYPE PDUSessionResourceToReleaseListHOCmd

PRESENCE optional
}|

{ ID id-TargetToSource-TransparentContainer

CRITICALITY reject TYPE TargetToSource-TransparentContainer

PRESENCE mandatory
}|

{ ID id-CriticalityDiagnostics

CRITICALITY ignore TYPE CriticalityDiagnostics

PRESENCE optional
},

...
}

-- **************************************************************

--
-- HANDOVER PREPARATION FAILURE
--
-- **************************************************************

HandoverPreparationFailure ::= SEQUENCE {

protocolIEs
ProtocolIE-Container

{ {HandoverPreparationFailureIEs} },

...
}

HandoverPreparationFailureIEs NGAP-PROTOCOL-IES ::= {

{ ID id-AMF-UE-NGAP-ID

CRITICALITY ignore TYPE AMF-UE-NGAP-ID

PRESENCE mandatory
}|

{ ID id-RAN-UE-NGAP-ID

CRITICALITY ignore TYPE RAN-UE-NGAP-ID

PRESENCE mandatory
}|

{ ID id-Cause

CRITICALITY ignore TYPE Cause

PRESENCE mandatory
}|

{ ID id-CriticalityDiagnostics
CRITICALITY ignore TYPE CriticalityDiagnostics
PRESENCE optional
}|

{ ID id-TargettoSource-Failure-TransparentContainer
CRITICALITY ignore TYPE TargettoSource-Failure-TransparentContainer
PRESENCE
optional

},

...
}

-- **************************************************************
--
-- Handover Resource Allocation Elementary Procedure
--
-- **************************************************************

-- **************************************************************
--
-- HANDOVER REQUEST
--
-- **************************************************************

HandoverRequest ::= SEQUENCE {

protocolIEs
ProtocolIE-Container

{ {HandoverRequestIEs} },

...
}

HandoverRequestIEs NGAP-PROTOCOL-IES ::= {

{ ID id-AMF-UE-NGAP-ID

CRITICALITY reject TYPE AMF-UE-NGAP-ID

PRESENCE mandatory
}|

{ ID id-HandoverType

CRITICALITY reject TYPE HandoverType

PRESENCE mandatory
}|

{ ID id-Cause

CRITICALITY ignore TYPE Cause

PRESENCE mandatory
}|

{ ID id-UEAggregateMaximumBitRate

CRITICALITY reject TYPE UEAggregateMaximumBitRate

PRESENCE mandatory
}|

{ ID id-CoreNetworkAssistanceInformationForInactive
CRITICALITY ignore TYPE CoreNetworkAssistanceInformationForInactive
PRESENCE
optional

}|

{ ID id-UESecurityCapabilities

CRITICALITY reject TYPE UESecurityCapabilities

PRESENCE mandatory
}|

{ ID id-SecurityContext

CRITICALITY reject TYPE SecurityContext

PRESENCE mandatory
}|

{ ID id-NewSecurityContextInd

CRITICALITY reject TYPE NewSecurityContextInd

PRESENCE optional
}|

{ ID id-NASC

CRITICALITY reject TYPE NAS-PDU

PRESENCE optional
}|

{ ID id-PDUSessionResourceSetupListHOReq

CRITICALITY reject TYPE PDUSessionResourceSetupListHOReq

PRESENCE mandatory
}|

{ ID id-AllowedNSSAI

CRITICALITY reject TYPE AllowedNSSAI

PRESENCE mandatory
}|

{ ID id-TraceActivation

CRITICALITY ignore TYPE TraceActivation

PRESENCE optional
}|

{ ID id-MaskedIMEISV

CRITICALITY ignore TYPE MaskedIMEISV

PRESENCE optional
}|

{ ID id-SourceToTarget-TransparentContainer
CRITICALITY reject TYPE SourceToTarget-TransparentContainer
PRESENCE mandatory
}|

{ ID id-MobilityRestrictionList

CRITICALITY ignore TYPE MobilityRestrictionList

PRESENCE optional
}|

{ ID id-LocationReportingRequestType

CRITICALITY ignore TYPE LocationReportingRequestType

PRESENCE optional
}|

{ ID id-RRCInactiveTransitionReportRequest
CRITICALITY ignore TYPE RRCInactiveTransitionReportRequest
PRESENCE optional
}|

{ ID id-GUAMI

CRITICALITY reject TYPE GUAMI

PRESENCE mandatory
}|

{ ID id-RedirectionVoiceFallback

CRITICALITY ignore TYPE RedirectionVoiceFallback

PRESENCE optional
}|

{ ID id-CNAssistedRANTuning

CRITICALITY ignore TYPE CNAssistedRANTuning

PRESENCE optional
}|

{ ID id-SRVCCOperationPossible

CRITICALITY ignore TYPE SRVCCOperationPossible

PRESENCE optional
}|

{ ID id-IAB-Authorized

CRITICALITY reject TYPE IAB-Authorized

PRESENCE optional
}|

{ ID id-Enhanced-CoverageRestriction

CRITICALITY ignore TYPE Enhanced-CoverageRestriction

PRESENCE optional
}|

{ ID id-UE-DifferentiationInfo

CRITICALITY ignore TYPE UE-DifferentiationInfo

PRESENCE optional
}|

{ ID id-NRV2XServicesAuthorized

CRITICALITY ignore TYPE NRV2XServicesAuthorized

PRESENCE optional
}|

{ ID id-LTEV2XServicesAuthorized

CRITICALITY ignore TYPE LTEV2XServicesAuthorized

PRESENCE optional
}|

{ ID id-NRUESidelinkAggregateMaximumBitrate
CRITICALITY ignore TYPE NRUESidelinkAggregateMaximumBitrate
PRESENCE optional
}|

{ ID id-LTEUESidelinkAggregateMaximumBitrate
CRITICALITY ignore TYPE LTEUESidelinkAggregateMaximumBitrate
PRESENCE optional
}|

{ ID id-PC5QoSParameters

CRITICALITY ignore TYPE PC5QoSParameters

PRESENCE optional
}|

{ ID id-CEmodeBrestricted

CRITICALITY ignore TYPE CEmodeBrestricted

PRESENCE optional
}|

{ ID id-UE-UP-CIoT-Support

CRITICALITY ignore TYPE UE-UP-CIoT-Support

PRESENCE optional
}|

{ ID id-ManagementBasedMDTPLMNList

CRITICALITY ignore TYPE MDTPLMNList

PRESENCE optional
}|

{ ID id-UERadioCapabilityID

CRITICALITY reject TYPE UERadioCapabilityID

PRESENCE optional
}|

{ ID id-Extended-ConnectedTime

CRITICALITY ignore TYPE Extended-ConnectedTime

PRESENCE optional
}|

{ ID id-TimeSyncAssistanceInfo

CRITICALITY ignore TYPE TimeSyncAssistanceInfo

PRESENCE optional
}|

{ ID id-UESliceMaximumBitRateList

CRITICALITY ignore TYPE UESliceMaximumBitRateList

PRESENCE optional
}|

{ ID id-FiveG-ProSeAuthorized

CRITICALITY ignore TYPE FiveG-ProSeAuthorized

PRESENCE optional
}|

{ ID id-FiveG-ProSeUEPC5AggregateMaximumBitRate CRITICALITY ignore TYPE NRUESidelinkAggregateMaximumBitrate
PRESENCE optional
}|

{ ID id-FiveG-ProSePC5QoSParameters

CRITICALITY ignore TYPE FiveG-ProSePC5QoSParameters

PRESENCE optional
}|

{ ID id-AerialUEsubscriptionInformation

CRITICALITY ignore TYPE AerialUEsubscriptionInformation

PRESENCE optional
}|

{ ID id-NR-A2X-ServicesAuthorized

CRITICALITY ignore TYPE NR-A2X-ServicesAuthorized

PRESENCE optional
}|

{ ID id-LTE-A2X-ServicesAuthorized

CRITICALITY ignore TYPE LTE-A2X-ServicesAuthorized

PRESENCE optional
}|

{ ID id-NR-A2X-UE-PC5-AggregateMaximumBitRate
CRITICALITY ignore TYPE NRUESidelinkAggregateMaximumBitrate
PRESENCE optional
}|

{ ID id-LTE-A2X-UE-PC5-AggregateMaximumBitRate CRITICALITY ignore TYPE LTEUESidelinkAggregateMaximumBitrate
PRESENCE optional
}|

{ ID id-A2X-PC5-QoS-Parameters

CRITICALITY ignore TYPE A2X-PC5-QoS-Parameters

PRESENCE optional
}|

{ ID id-MobileIAB-Authorized

CRITICALITY ignore TYPE MobileIAB-Authorized

PRESENCE optional
}|

{ ID id-NoPDUSessionIndication

CRITICALITY ignore TYPE NoPDUSessionIndication

PRESENCE optional
}|

{ ID id-Partially-Allowed-NSSAI

CRITICALITY ignore TYPE Partially-Allowed-NSSAI

PRESENCE optional
}|

{ ID id-SLPositioningRangingServiceInfo

CRITICALITY ignore TYPE SLPositioningRangingServiceInfo

PRESENCE optional
}|

{ ID id-AMF-UE-NGAP-ID2

CRITICALITY ignore TYPE AMF-UE-NGAP-ID

PRESENCE optional
}|

{ ID id-Target-RAN-Node-ID

CRITICALITY ignore TYPE GlobalRANNodeID

PRESENCE optional
},

...
}

-- **************************************************************
--
-- HANDOVER REQUEST ACKNOWLEDGE
--
-- **************************************************************

HandoverRequestAcknowledge ::= SEQUENCE {

protocolIEs
ProtocolIE-Container

{ {HandoverRequestAcknowledgeIEs} },

...
}

HandoverRequestAcknowledgeIEs NGAP-PROTOCOL-IES ::= {

{ ID id-AMF-UE-NGAP-ID

CRITICALITY ignore TYPE AMF-UE-NGAP-ID

PRESENCE mandatory
}|

{ ID id-RAN-UE-NGAP-ID

CRITICALITY ignore TYPE RAN-UE-NGAP-ID

PRESENCE mandatory
}|

{ ID id-PDUSessionResourceAdmittedList

CRITICALITY ignore TYPE PDUSessionResourceAdmittedList

PRESENCE mandatory
}|

{ ID id-PDUSessionResourceFailedToSetupListHOAck
CRITICALITY ignore TYPE PDUSessionResourceFailedToSetupListHOAck
PRESENCE optional
}|

{ ID id-TargetToSource-TransparentContainer

CRITICALITY reject TYPE TargetToSource-TransparentContainer

PRESENCE mandatory
}|

{ ID id-CriticalityDiagnostics

CRITICALITY ignore TYPE CriticalityDiagnostics

PRESENCE optional
}|

{ ID id-NPN-AccessInformation

CRITICALITY reject TYPE NPN-AccessInformation

PRESENCE optional
}|

{ ID id-RedCapIndication

CRITICALITY ignore TYPE RedCapIndication

PRESENCE optional
}|

{ ID id-ERedCapIndication

CRITICALITY ignore TYPE ERedCapIndication

PRESENCE optional
},

...
}

-- **************************************************************
--
-- HANDOVER FAILURE
--
-- **************************************************************

HandoverFailure ::= SEQUENCE {

protocolIEs
ProtocolIE-Container

{ { HandoverFailureIEs} },

...
}

HandoverFailureIEs NGAP-PROTOCOL-IES ::= {

{ ID id-AMF-UE-NGAP-ID

CRITICALITY ignore TYPE AMF-UE-NGAP-ID

PRESENCE mandatory
}|

{ ID id-Cause

CRITICALITY ignore TYPE Cause

PRESENCE mandatory
}|

{ ID id-CriticalityDiagnostics
CRITICALITY ignore TYPE CriticalityDiagnostics
PRESENCE optional
}|

{ ID id-TargettoSource-Failure-TransparentContainer
CRITICALITY ignore TYPE TargettoSource-Failure-TransparentContainer
PRESENCE
optional

},

...
}

-- **************************************************************
--
-- Handover Notification Elementary Procedure
--
-- **************************************************************

-- **************************************************************
--
-- HANDOVER NOTIFY
--
-- **************************************************************

HandoverNotify ::= SEQUENCE {

protocolIEs
ProtocolIE-Container

{ { HandoverNotifyIEs} },

...
}

HandoverNotifyIEs NGAP-PROTOCOL-IES ::= {

{ ID id-AMF-UE-NGAP-ID

CRITICALITY reject TYPE AMF-UE-NGAP-ID

PRESENCE mandatory
}|

{ ID id-RAN-UE-NGAP-ID

CRITICALITY reject TYPE RAN-UE-NGAP-ID

PRESENCE mandatory
}|

{ ID id-UserLocationInformation
CRITICALITY ignore TYPE UserLocationInformation
PRESENCE mandatory
}|

{ ID id-NotifySourceNGRANNode

CRITICALITY ignore TYPE NotifySourceNGRANNode
PRESENCE optional    },

...
}

-- **************************************************************
--
-- Path Switch Request Elementary Procedure
--
-- **************************************************************

-- **************************************************************
--
-- PATH SWITCH REQUEST
--
-- **************************************************************

PathSwitchRequest ::= SEQUENCE {

protocolIEs
ProtocolIE-Container

{ { PathSwitchRequestIEs} },

...
}

PathSwitchRequestIEs NGAP-PROTOCOL-IES ::= {

{ ID id-RAN-UE-NGAP-ID

CRITICALITY reject TYPE RAN-UE-NGAP-ID

PRESENCE mandatory
}|

{ ID id-SourceAMF-UE-NGAP-ID

CRITICALITY reject TYPE AMF-UE-NGAP-ID

PRESENCE mandatory
}|

{ ID id-UserLocationInformation

CRITICALITY ignore TYPE UserLocationInformation

PRESENCE mandatory
}|

{ ID id-UESecurityCapabilities

CRITICALITY ignore TYPE UESecurityCapabilities

PRESENCE mandatory
}|

{ ID id-PDUSessionResourceToBeSwitchedDLList

CRITICALITY reject TYPE PDUSessionResourceToBeSwitchedDLList

PRESENCE mandatory
}|

{ ID id-PDUSessionResourceFailedToSetupListPSReq
CRITICALITY ignore TYPE PDUSessionResourceFailedToSetupListPSReq
PRESENCE optional
}|

{ ID id-RRC-Resume-Cause

CRITICALITY ignore TYPE RRCEstablishmentCause

PRESENCE optional
}|

{ ID id-RedCapIndication

CRITICALITY ignore TYPE RedCapIndication

PRESENCE optional
}|

{ ID id-ERedCapIndication

CRITICALITY ignore TYPE ERedCapIndication

PRESENCE optional
}|

{ ID id-SourceAMF-GUAMI

CRITICALITY ignore TYPE GUAMI

PRESENCE optional
},

...
}

-- **************************************************************
--
-- PATH SWITCH REQUEST ACKNOWLEDGE
--
-- **************************************************************

PathSwitchRequestAcknowledge ::= SEQUENCE {

protocolIEs
ProtocolIE-Container

{ { PathSwitchRequestAcknowledgeIEs} },

...
}

PathSwitchRequestAcknowledgeIEs NGAP-PROTOCOL-IES ::= {

{ ID id-AMF-UE-NGAP-ID

CRITICALITY ignore TYPE AMF-UE-NGAP-ID

PRESENCE mandatory
}|

{ ID id-RAN-UE-NGAP-ID

CRITICALITY ignore TYPE RAN-UE-NGAP-ID

PRESENCE mandatory
}|

{ ID id-UESecurityCapabilities

CRITICALITY reject TYPE UESecurityCapabilities

PRESENCE optional
}|

{ ID id-SecurityContext

CRITICALITY reject TYPE SecurityContext

PRESENCE mandatory
}|

{ ID id-NewSecurityContextInd

CRITICALITY reject TYPE NewSecurityContextInd

PRESENCE optional
}|

{ ID id-PDUSessionResourceSwitchedList

CRITICALITY ignore TYPE PDUSessionResourceSwitchedList

PRESENCE mandatory
}|

{ ID id-PDUSessionResourceReleasedListPSAck

CRITICALITY ignore TYPE PDUSessionResourceReleasedListPSAck
PRESENCE optional
}|

{ ID id-AllowedNSSAI

CRITICALITY reject TYPE AllowedNSSAI

PRESENCE mandatory
}|

{ ID id-CoreNetworkAssistanceInformationForInactive
CRITICALITY ignore TYPE CoreNetworkAssistanceInformationForInactive
PRESENCE
optional

}|

{ ID id-RRCInactiveTransitionReportRequest

CRITICALITY ignore TYPE RRCInactiveTransitionReportRequest

PRESENCE optional
}|

{ ID id-CriticalityDiagnostics

CRITICALITY ignore TYPE CriticalityDiagnostics

PRESENCE optional
}|

{ ID id-RedirectionVoiceFallback

CRITICALITY ignore TYPE RedirectionVoiceFallback

PRESENCE optional
}|

{ ID id-CNAssistedRANTuning

CRITICALITY ignore TYPE CNAssistedRANTuning

PRESENCE optional
}|

{ ID id-SRVCCOperationPossible

CRITICALITY ignore TYPE SRVCCOperationPossible

PRESENCE optional
}|

{ ID id-Enhanced-CoverageRestriction

CRITICALITY ignore TYPE Enhanced-CoverageRestriction

PRESENCE optional
}|

{ ID id-Extended-ConnectedTime

CRITICALITY ignore TYPE Extended-ConnectedTime

PRESENCE optional
}|

{ ID id-UE-DifferentiationInfo

CRITICALITY ignore TYPE UE-DifferentiationInfo

PRESENCE optional
}|

{ ID id-NRV2XServicesAuthorized

CRITICALITY ignore TYPE NRV2XServicesAuthorized

PRESENCE optional
}|

{ ID id-LTEV2XServicesAuthorized

CRITICALITY ignore TYPE LTEV2XServicesAuthorized

PRESENCE optional
}|

{ ID id-NRUESidelinkAggregateMaximumBitrate

CRITICALITY ignore TYPE NRUESidelinkAggregateMaximumBitrate
PRESENCE optional
}|

{ ID id-LTEUESidelinkAggregateMaximumBitrate

CRITICALITY ignore TYPE LTEUESidelinkAggregateMaximumBitrate
PRESENCE optional
}|

{ ID id-PC5QoSParameters

CRITICALITY ignore TYPE PC5QoSParameters

PRESENCE optional
}|

{ ID id-CEmodeBrestricted

CRITICALITY ignore TYPE CEmodeBrestricted

PRESENCE optional
}|

{ ID id-UE-UP-CIoT-Support

CRITICALITY ignore TYPE UE-UP-CIoT-Support

PRESENCE optional
}|

{ ID id-UERadioCapabilityID

CRITICALITY reject TYPE UERadioCapabilityID

PRESENCE optional
}|

{ ID id-ManagementBasedMDTPLMNList

CRITICALITY ignore TYPE MDTPLMNList

PRESENCE optional
}|

{ ID id-TimeSyncAssistanceInfo

CRITICALITY ignore TYPE TimeSyncAssistanceInfo

PRESENCE optional
}|

{ ID id-FiveG-ProSeAuthorized

CRITICALITY ignore TYPE FiveG-ProSeAuthorized

PRESENCE optional
}|

{ ID id-FiveG-ProSeUEPC5AggregateMaximumBitRate
CRITICALITY ignore TYPE NRUESidelinkAggregateMaximumBitrate
PRESENCE optional
}|

{ ID id-FiveG-ProSePC5QoSParameters

CRITICALITY ignore TYPE FiveG-ProSePC5QoSParameters

PRESENCE optional
}|

{ ID id-ManagementBasedMDTPLMNModificationList
CRITICALITY ignore TYPE MDTPLMNModificationList

PRESENCE optional
}|

{ ID id-IAB-Authorized

CRITICALITY ignore TYPE IAB-Authorized

PRESENCE optional
}|

{ ID id-AerialUEsubscriptionInformation

CRITICALITY ignore TYPE AerialUEsubscriptionInformation

PRESENCE optional
}|

{ ID id-NR-A2X-ServicesAuthorized

CRITICALITY ignore TYPE NR-A2X-ServicesAuthorized

PRESENCE optional
}|

{ ID id-LTE-A2X-ServicesAuthorized

CRITICALITY ignore TYPE LTE-A2X-ServicesAuthorized

PRESENCE optional
}|

{ ID id-NR-A2X-UE-PC5-AggregateMaximumBitRate

CRITICALITY ignore TYPE NRUESidelinkAggregateMaximumBitrate
PRESENCE optional
}|

{ ID id-LTE-A2X-UE-PC5-AggregateMaximumBitRate
CRITICALITY ignore TYPE LTEUESidelinkAggregateMaximumBitrate
PRESENCE optional
}|

{ ID id-A2X-PC5-QoS-Parameters

CRITICALITY ignore TYPE A2X-PC5-QoS-Parameters

PRESENCE optional
}|

{ ID id-MobileIAB-Authorized

        CRITICALITY ignore TYPE MobileIAB-Authorized

PRESENCE optional
}|

{ ID id-Partially-Allowed-NSSAI

CRITICALITY ignore TYPE Partially-Allowed-NSSAI

PRESENCE optional
}|

{ ID id-SLPositioningRangingServiceInfo

CRITICALITY ignore TYPE SLPositioningRangingServiceInfo

PRESENCE optional
}|

{ ID id-AMF-UE-NGAP-ID2

CRITICALITY ignore TYPE AMF-UE-NGAP-ID

PRESENCE optional
},

...
}

-- **************************************************************
--
-- PATH SWITCH REQUEST FAILURE
--
-- **************************************************************

PathSwitchRequestFailure ::= SEQUENCE {

protocolIEs
ProtocolIE-Container

{ { PathSwitchRequestFailureIEs} },

...
}

PathSwitchRequestFailureIEs NGAP-PROTOCOL-IES ::= {

{ ID id-AMF-UE-NGAP-ID

CRITICALITY ignore TYPE AMF-UE-NGAP-ID

PRESENCE mandatory
}|

{ ID id-RAN-UE-NGAP-ID

CRITICALITY ignore TYPE RAN-UE-NGAP-ID

PRESENCE mandatory
}|

{ ID id-PDUSessionResourceReleasedListPSFail
CRITICALITY ignore TYPE PDUSessionResourceReleasedListPSFail
PRESENCE mandatory
}|

{ ID id-CriticalityDiagnostics

CRITICALITY ignore TYPE CriticalityDiagnostics

PRESENCE optional
},

...
}

-- **************************************************************
--
-- Handover Cancellation Elementary Procedure
--
-- **************************************************************

-- **************************************************************
--
-- HANDOVER CANCEL
--
-- **************************************************************

HandoverCancel ::= SEQUENCE {

protocolIEs
ProtocolIE-Container

{ { HandoverCancelIEs} },

...
}

HandoverCancelIEs NGAP-PROTOCOL-IES ::= {

{ ID id-AMF-UE-NGAP-ID
CRITICALITY reject TYPE AMF-UE-NGAP-ID
PRESENCE mandatory }|

{ ID id-RAN-UE-NGAP-ID
CRITICALITY reject TYPE RAN-UE-NGAP-ID
PRESENCE mandatory }|

{ ID id-Cause

CRITICALITY ignore TYPE Cause

PRESENCE mandatory },

...
}

-- **************************************************************
--
-- HANDOVER CANCEL ACKNOWLEDGE
--
-- **************************************************************

HandoverCancelAcknowledge ::= SEQUENCE {

protocolIEs
ProtocolIE-Container

{ { HandoverCancelAcknowledgeIEs} },

...
}

HandoverCancelAcknowledgeIEs NGAP-PROTOCOL-IES ::= {

{ ID id-AMF-UE-NGAP-ID

CRITICALITY ignore TYPE AMF-UE-NGAP-ID

PRESENCE mandatory
}|

{ ID id-RAN-UE-NGAP-ID

CRITICALITY ignore TYPE RAN-UE-NGAP-ID

PRESENCE mandatory
}|

{ ID id-CriticalityDiagnostics
CRITICALITY ignore TYPE CriticalityDiagnostics
PRESENCE optional
},

...
}

-- **************************************************************
--
-- HANDOVER SUCCESS ELEMENTARY PROCEDURE
--
-- **************************************************************

-- **************************************************************
--

-- HANDOVER SUCCESS
--
-- **************************************************************

HandoverSuccess ::= SEQUENCE {

protocolIEs

ProtocolIE-Container       { { HandoverSuccessIEs} },

...
}

HandoverSuccessIEs NGAP-PROTOCOL-IES ::= {

{ ID id-AMF-UE-NGAP-ID
CRITICALITY reject TYPE AMF-UE-NGAP-ID
PRESENCE mandatory }|

{ ID id-RAN-UE-NGAP-ID
CRITICALITY reject TYPE RAN-UE-NGAP-ID
PRESENCE mandatory },

...
}

-- **************************************************************
--
-- UPLINK RAN EARLY STATUS TRANSFER ELEMENTARY PROCEDURE
--
-- **************************************************************

-- **************************************************************
--
-- Uplink RAN Early Status Transfer
--
-- **************************************************************

UplinkRANEarlyStatusTransfer ::= SEQUENCE {

protocolIEs

ProtocolIE-Container       { {UplinkRANEarlyStatusTransferIEs} },

...
}

UplinkRANEarlyStatusTransferIEs NGAP-PROTOCOL-IES ::= {

{ ID id-AMF-UE-NGAP-ID

CRITICALITY reject TYPE AMF-UE-NGAP-ID

PRESENCE mandatory
}|

{ ID id-RAN-UE-NGAP-ID

CRITICALITY reject TYPE RAN-UE-NGAP-ID

PRESENCE mandatory
}|

{ ID id-EarlyStatusTransfer-TransparentContainer    CRITICALITY reject  TYPE EarlyStatusTransfer-TransparentContainer
PRESENCE mandatory
},

...
}

-- **************************************************************
--
-- DOWNLINK RAN EARLY STATUS TRANSFER ELEMENTARY PROCEDURE
--
-- **************************************************************

-- **************************************************************
--
-- Downlink RAN Early Status Transfer
--
-- **************************************************************

DownlinkRANEarlyStatusTransfer ::= SEQUENCE {

protocolIEs

ProtocolIE-Container       { {DownlinkRANEarlyStatusTransferIEs} },

...

}

DownlinkRANEarlyStatusTransferIEs NGAP-PROTOCOL-IES ::= {

{ ID id-AMF-UE-NGAP-ID

CRITICALITY reject TYPE AMF-UE-NGAP-ID

PRESENCE mandatory
}|

{ ID id-RAN-UE-NGAP-ID

CRITICALITY reject TYPE RAN-UE-NGAP-ID

PRESENCE mandatory
}|

{ ID id-EarlyStatusTransfer-TransparentContainer
CRITICALITY reject TYPE EarlyStatusTransfer-TransparentContainer
PRESENCE mandatory
},

...
}

-- **************************************************************
--
-- Uplink RAN Status Transfer Elementary Procedure
--
-- **************************************************************

-- **************************************************************
--
-- UPLINK RAN STATUS TRANSFER
--
-- **************************************************************

UplinkRANStatusTransfer ::= SEQUENCE {

protocolIEs
ProtocolIE-Container

{ {UplinkRANStatusTransferIEs} },

...
}

UplinkRANStatusTransferIEs NGAP-PROTOCOL-IES ::= {

{ ID id-AMF-UE-NGAP-ID

CRITICALITY reject TYPE AMF-UE-NGAP-ID

PRESENCE mandatory
}|

{ ID id-RAN-UE-NGAP-ID

CRITICALITY reject TYPE RAN-UE-NGAP-ID

PRESENCE mandatory
}|

{ ID id-RANStatusTransfer-TransparentContainer
CRITICALITY reject TYPE RANStatusTransfer-TransparentContainer PRESENCE mandatory
},

...
}

-- **************************************************************
--
-- Downlink RAN Status Transfer Elementary Procedure
--
-- **************************************************************

-- **************************************************************
--
-- DOWNLINK RAN STATUS TRANSFER
--
-- **************************************************************

DownlinkRANStatusTransfer ::= SEQUENCE {

protocolIEs
ProtocolIE-Container

{ {DownlinkRANStatusTransferIEs} },

...
}

DownlinkRANStatusTransferIEs NGAP-PROTOCOL-IES ::= {

{ ID id-AMF-UE-NGAP-ID

CRITICALITY reject TYPE AMF-UE-NGAP-ID

PRESENCE mandatory
}|

{ ID id-RAN-UE-NGAP-ID

CRITICALITY reject TYPE RAN-UE-NGAP-ID

PRESENCE mandatory
}|

{ ID id-RANStatusTransfer-TransparentContainer
CRITICALITY reject TYPE RANStatusTransfer-TransparentContainer
PRESENCE mandatory
},

...
}

-- **************************************************************
--
-- PAGING ELEMENTARY PROCEDURE
--
-- **************************************************************

-- **************************************************************
--
-- PAGING
--
-- **************************************************************

Paging ::= SEQUENCE {

protocolIEs
ProtocolIE-Container

{ {PagingIEs} },

...
}

PagingIEs NGAP-PROTOCOL-IES ::= {

{ ID id-UEPagingIdentity

CRITICALITY ignore TYPE UEPagingIdentity

PRESENCE mandatory
}|

{ ID id-PagingDRX

CRITICALITY ignore TYPE PagingDRX

PRESENCE optional
}|

{ ID id-TAIListForPaging

CRITICALITY ignore TYPE TAIListForPaging

PRESENCE mandatory
}|

{ ID id-PagingPriority

CRITICALITY ignore TYPE PagingPriority

PRESENCE optional
}|

{ ID id-UERadioCapabilityForPaging
CRITICALITY ignore TYPE UERadioCapabilityForPaging
PRESENCE optional
}|

{ ID id-PagingOrigin

CRITICALITY ignore TYPE PagingOrigin

PRESENCE optional
}|

{ ID id-AssistanceDataForPaging

CRITICALITY ignore TYPE AssistanceDataForPaging

PRESENCE optional
}|

{ ID id-NB-IoT-Paging-eDRXInfo

CRITICALITY ignore TYPE NB-IoT-Paging-eDRXInfo

PRESENCE optional
}|

{ ID id-NB-IoT-PagingDRX

CRITICALITY ignore TYPE NB-IoT-PagingDRX

PRESENCE optional
}|

{ ID id-Enhanced-CoverageRestriction
CRITICALITY ignore TYPE Enhanced-CoverageRestriction
PRESENCE optional
}|

{ ID id-WUS-Assistance-Information
CRITICALITY ignore TYPE WUS-Assistance-Information
PRESENCE optional
}|

{ ID id-EUTRA-PagingeDRXInformation
CRITICALITY ignore TYPE EUTRA-PagingeDRXInformation
PRESENCE optional
}|

{ ID id-CEmodeBrestricted

CRITICALITY ignore TYPE CEmodeBrestricted

PRESENCE optional
}|

{ ID id-NR-PagingeDRXInformation

CRITICALITY ignore TYPE NR-PagingeDRXInformation

PRESENCE optional
}|

{ ID id-PagingCause

CRITICALITY ignore TYPE PagingCause

PRESENCE optional
}|

{ ID id-PEIPSassistanceInformation
CRITICALITY ignore TYPE PEIPSassistanceInformation
PRESENCE optional
}|

{ ID id-LPWUSPSAssistanceInformation
CRITICALITY ignore TYPE LPWUSPSAssistanceInformation
PRESENCE optional
}|

{ ID id-LPWUSDisableIndication
CRITICALITY ignore TYPE LPWUSDisableIndication
    PRESENCE optional
},

...
}

-- **************************************************************
--
-- NAS TRANSPORT ELEMENTARY PROCEDURES
--
-- **************************************************************

-- **************************************************************
--
-- INITIAL UE MESSAGE
--
-- **************************************************************

InitialUEMessage ::= SEQUENCE {

protocolIEs
ProtocolIE-Container

{ {InitialUEMessage-IEs} },

...
}

InitialUEMessage-IEs NGAP-PROTOCOL-IES ::= {

{ ID id-RAN-UE-NGAP-ID

CRITICALITY reject TYPE RAN-UE-NGAP-ID

PRESENCE mandatory
}|

{ ID id-NAS-PDU

CRITICALITY reject TYPE NAS-PDU

PRESENCE mandatory
}|

{ ID id-UserLocationInformation

CRITICALITY reject TYPE UserLocationInformation

PRESENCE mandatory
}|

{ ID id-RRCEstablishmentCause

CRITICALITY ignore TYPE RRCEstablishmentCause

PRESENCE mandatory
}|

{ ID id-FiveG-S-TMSI

CRITICALITY reject TYPE FiveG-S-TMSI

PRESENCE optional
}|

{ ID id-AMFSetID

CRITICALITY ignore TYPE AMFSetID

PRESENCE optional
}|

{ ID id-UEContextRequest

CRITICALITY ignore TYPE UEContextRequest

PRESENCE optional
}|

{ ID id-AllowedNSSAI

CRITICALITY reject TYPE AllowedNSSAI

PRESENCE optional
}|

{ ID id-SourceToTarget-AMFInformationReroute
CRITICALITY ignore TYPE SourceToTarget-AMFInformationReroute
PRESENCE optional
}|

{ ID id-SelectedPLMNIdentity

CRITICALITY ignore TYPE PLMNIdentity

PRESENCE optional
}|

{ ID id-IABNodeIndication

CRITICALITY reject TYPE IABNodeIndication

PRESENCE optional
}|

{ ID id-CEmodeBSupport-Indicator

CRITICALITY reject TYPE CEmodeBSupport-Indicator

PRESENCE optional
}|

{ ID id-LTEM-Indication

CRITICALITY ignore TYPE LTEM-Indication

PRESENCE optional
}|

{ ID id-EDT-Session

CRITICALITY ignore TYPE EDT-Session

PRESENCE optional
}|

{ ID id-AuthenticatedIndication

CRITICALITY ignore TYPE AuthenticatedIndication

PRESENCE optional
}|

{ ID id-NPN-AccessInformation

CRITICALITY reject TYPE NPN-AccessInformation

PRESENCE optional
}|

{ ID id-RedCapIndication

CRITICALITY ignore TYPE RedCapIndication

PRESENCE optional
}|

{ ID id-SelectedNID

CRITICALITY ignore TYPE NID

PRESENCE optional
}|

{ ID id-MobileIABNodeIndication

CRITICALITY reject TYPE MobileIABNodeIndication

PRESENCE optional
}|

{ ID id-Partially-Allowed-NSSAI

CRITICALITY ignore TYPE Partially-Allowed-NSSAI

PRESENCE optional
}|

{ ID id-ERedCapIndication

CRITICALITY ignore TYPE ERedCapIndication

PRESENCE optional
}|

{ ID id-AUN3DeviceAccessInfo

CRITICALITY ignore TYPE AUN3DeviceAccessInfo

PRESENCE optional
}|

{ ID id-GUAMI

CRITICALITY ignore TYPE GUAMI

PRESENCE optional
}|

{ ID id-GUAMIType

CRITICALITY ignore TYPE GUAMIType

PRESENCE optional
}|

{ ID id-RequestedNSSAI

CRITICALITY ignore TYPE RequestedNSSAI

PRESENCE optional
},

...
}

-- **************************************************************
--
-- DOWNLINK NAS TRANSPORT
--
-- **************************************************************

DownlinkNASTransport ::= SEQUENCE {

protocolIEs
ProtocolIE-Container

{ {DownlinkNASTransport-IEs} },

...
}

DownlinkNASTransport-IEs NGAP-PROTOCOL-IES ::= {

{ ID id-AMF-UE-NGAP-ID

CRITICALITY reject TYPE AMF-UE-NGAP-ID

 PRESENCE mandatory
}|

{ ID id-RAN-UE-NGAP-ID

CRITICALITY reject TYPE RAN-UE-NGAP-ID

 PRESENCE mandatory
}|

{ ID id-OldAMF

CRITICALITY reject TYPE AMFName

 PRESENCE optional
}|

{ ID id-RANPagingPriority

CRITICALITY ignore TYPE RANPagingPriority

 PRESENCE optional
}|

{ ID id-NAS-PDU

CRITICALITY reject TYPE NAS-PDU

 PRESENCE mandatory
}|

{ ID id-MobilityRestrictionList

CRITICALITY ignore TYPE MobilityRestrictionList
 PRESENCE optional
}|

{ ID id-IndexToRFSP

CRITICALITY ignore TYPE IndexToRFSP

 PRESENCE optional
}|

{ ID id-UEAggregateMaximumBitRate

CRITICALITY ignore TYPE UEAggregateMaximumBitRate  PRESENCE optional
}|

{ ID id-AllowedNSSAI

CRITICALITY reject TYPE AllowedNSSAI

 PRESENCE optional
}|

{ ID id-SRVCCOperationPossible

CRITICALITY ignore TYPE SRVCCOperationPossible
 PRESENCE optional
}|

{ ID id-Enhanced-CoverageRestriction
CRITICALITY ignore TYPE Enhanced-CoverageRestriction PRESENCE optional
}|

{ ID id-Extended-ConnectedTime

CRITICALITY ignore TYPE Extended-ConnectedTime
 PRESENCE optional
}|

{ ID id-UE-DifferentiationInfo

CRITICALITY ignore TYPE UE-DifferentiationInfo
 PRESENCE optional
}|

{ ID id-CEmodeBrestricted

CRITICALITY ignore TYPE CEmodeBrestricted

 PRESENCE optional
}|

{ ID id-UERadioCapability

CRITICALITY ignore TYPE UERadioCapability

 PRESENCE optional
}|

{ ID id-UECapabilityInfoRequest

CRITICALITY ignore TYPE UECapabilityInfoRequest
 PRESENCE optional
}|

{ ID id-EndIndication

CRITICALITY ignore TYPE EndIndication

 PRESENCE optional
}|

{ ID id-UERadioCapabilityID

CRITICALITY reject TYPE UERadioCapabilityID

 PRESENCE optional
}|

{ ID id-TargetNSSAIInformation

CRITICALITY ignore TYPE TargetNSSAIInformation
 PRESENCE optional
}|

{ ID id-MaskedIMEISV

CRITICALITY ignore TYPE MaskedIMEISV

 PRESENCE optional
}|

{ ID id-Partially-Allowed-NSSAI

CRITICALITY ignore TYPE Partially-Allowed-NSSAI
 PRESENCE optional
}|

{ ID id-MobileIAB-Authorized

CRITICALITY ignore TYPE MobileIAB-Authorized

 PRESENCE optional
}|

{ ID id-ExtendedOldAMF

CRITICALITY ignore TYPE Extended-AMFName

 PRESENCE optional
},

...
}

-- **************************************************************
--
-- UPLINK NAS TRANSPORT
--
-- **************************************************************

UplinkNASTransport ::= SEQUENCE {

protocolIEs
ProtocolIE-Container
{ {UplinkNASTransport-IEs} },

...
}

UplinkNASTransport-IEs NGAP-PROTOCOL-IES ::= {

{ ID id-AMF-UE-NGAP-ID

CRITICALITY reject TYPE AMF-UE-NGAP-ID

PRESENCE mandatory }|

{ ID id-RAN-UE-NGAP-ID

CRITICALITY reject TYPE RAN-UE-NGAP-ID

PRESENCE mandatory }|

{ ID id-NAS-PDU

CRITICALITY reject TYPE NAS-PDU

PRESENCE mandatory }|

{ ID id-UserLocationInformation
CRITICALITY ignore TYPE UserLocationInformation

PRESENCE mandatory }|

{ ID id-W-AGFIdentityInformation
CRITICALITY reject TYPE OCTET STRING

PRESENCE optional
}|

{ ID id-TNGFIdentityInformation
CRITICALITY reject TYPE OCTET STRING

PRESENCE optional
}|

{ ID id-TWIFIdentityInformation
CRITICALITY reject TYPE OCTET STRING

PRESENCE optional
},

...
}

-- **************************************************************
--
-- NAS NON DELIVERY INDICATION
--
-- **************************************************************

NASNonDeliveryIndication ::= SEQUENCE {

protocolIEs
ProtocolIE-Container

{ {NASNonDeliveryIndication-IEs} },

...
}

NASNonDeliveryIndication-IEs NGAP-PROTOCOL-IES ::= {

{ ID id-AMF-UE-NGAP-ID
CRITICALITY reject TYPE AMF-UE-NGAP-ID
PRESENCE mandatory }|

{ ID id-RAN-UE-NGAP-ID
CRITICALITY reject TYPE RAN-UE-NGAP-ID
PRESENCE mandatory }|

{ ID id-NAS-PDU

CRITICALITY ignore TYPE NAS-PDU

PRESENCE mandatory }|

{ ID id-Cause

CRITICALITY ignore TYPE Cause

PRESENCE mandatory },

...
}

-- **************************************************************
--
-- REROUTE NAS REQUEST
--
-- **************************************************************

RerouteNASRequest ::= SEQUENCE {

protocolIEs
ProtocolIE-Container

{ {RerouteNASRequest-IEs} },

...
}

RerouteNASRequest-IEs NGAP-PROTOCOL-IES ::= {

{ ID id-RAN-UE-NGAP-ID

CRITICALITY reject TYPE RAN-UE-NGAP-ID

PRESENCE mandatory
}|

{ ID id-AMF-UE-NGAP-ID

CRITICALITY ignore TYPE AMF-UE-NGAP-ID

PRESENCE optional
}|

{ ID id-NGAP-Message

CRITICALITY reject TYPE OCTET STRING

PRESENCE mandatory
}|

{ ID id-AMFSetID

CRITICALITY reject TYPE AMFSetID

PRESENCE mandatory
}|

{ ID id-AllowedNSSAI

CRITICALITY reject TYPE AllowedNSSAI

PRESENCE optional
}|

{ ID id-SourceToTarget-AMFInformationReroute
CRITICALITY ignore TYPE SourceToTarget-AMFInformationReroute
PRESENCE optional
}|

{ ID id-Partially-Allowed-NSSAI

CRITICALITY ignore TYPE Partially-Allowed-NSSAI                PRESENCE optional
},

...
}

-- **************************************************************
--
-- INTERFACE MANAGEMENT ELEMENTARY PROCEDURES
--
-- **************************************************************

-- **************************************************************
--
-- NG Removal Elementary Procedure
--
-- **************************************************************

-- **************************************************************
--
-- NG REMOVAL REQUEST
--
-- **************************************************************

NGRemovalRequest ::= SEQUENCE {

protocolIEs
ProtocolIE-Container

{ {NGRemovalRequestIEs} },

...
}

NGRemovalRequestIEs NGAP-PROTOCOL-IES ::= {

{ ID id-GlobalRANNodeID

CRITICALITY reject TYPE GlobalRANNodeID

PRESENCE mandatory },

...

}

-- **************************************************************
--
-- NG REMOVAL RESPONSE
--
-- **************************************************************

NGRemovalResponse ::= SEQUENCE {

protocolIEs
ProtocolIE-Container

{ {NGRemovalResponseIEs} },

...
}

NGRemovalResponseIEs NGAP-PROTOCOL-IES ::= {

{ ID id-AMFName

CRITICALITY reject TYPE AMFName

PRESENCE mandatory
}|

{ ID id-CriticalityDiagnostics
CRITICALITY ignore TYPE CriticalityDiagnostics
PRESENCE optional
}|

{ ID id-Extended-AMFName

CRITICALITY ignore TYPE Extended-AMFName

PRESENCE optional
},

...
}

-- **************************************************************
--
-- NG REMOVAL FAILURE
--
-- **************************************************************

NGRemovalFailure ::= SEQUENCE {

protocolIEs
ProtocolIE-Container

{ {NGRemovalFailureIEs} },

...
}

NGRemovalFailureIEs NGAP-PROTOCOL-IES ::= {

{ ID id-Cause

CRITICALITY ignore TYPE Cause

PRESENCE mandatory
}|

{ ID id-CriticalityDiagnostics
CRITICALITY ignore TYPE CriticalityDiagnostics
PRESENCE optional
},

...
}

-- **************************************************************
--
-- NG Setup Elementary Procedure
--
-- **************************************************************

-- **************************************************************
--
-- NG SETUP REQUEST
--
-- **************************************************************

NGSetupRequest ::= SEQUENCE {

protocolIEs
ProtocolIE-Container

{ {NGSetupRequestIEs} },

...
}

NGSetupRequestIEs NGAP-PROTOCOL-IES ::= {

{ ID id-GlobalRANNodeID

CRITICALITY reject TYPE GlobalRANNodeID

PRESENCE mandatory }|

{ ID id-RANNodeName

CRITICALITY ignore TYPE RANNodeName

PRESENCE optional
}|

{ ID id-SupportedTAList

CRITICALITY reject TYPE SupportedTAList

PRESENCE mandatory }|

{ ID id-DefaultPagingDRX

CRITICALITY ignore TYPE PagingDRX

PRESENCE mandatory }|

{ ID id-UERetentionInformation
CRITICALITY ignore TYPE UERetentionInformation

PRESENCE optional
}|

{ ID id-NB-IoT-DefaultPagingDRX
CRITICALITY ignore TYPE NB-IoT-DefaultPagingDRX

PRESENCE optional
}|

{ ID id-Extended-RANNodeName

CRITICALITY ignore TYPE Extended-RANNodeName

PRESENCE optional
}|

{ ID id-AIoT-Support

CRITICALITY reject TYPE AIoT-Support

PRESENCE optional
}|

{ ID id-AdditionalULI

CRITICALITY ignore TYPE AdditionalULI

PRESENCE optional
},

...
}

-- **************************************************************
--
-- NG SETUP RESPONSE
--
-- **************************************************************

NGSetupResponse ::= SEQUENCE {

protocolIEs
ProtocolIE-Container

{ {NGSetupResponseIEs} },

...
}

NGSetupResponseIEs NGAP-PROTOCOL-IES ::= {

{ ID id-AMFName

CRITICALITY reject TYPE AMFName

PRESENCE mandatory
}|

{ ID id-ServedGUAMIList

CRITICALITY reject TYPE ServedGUAMIList

PRESENCE mandatory
}|

{ ID id-RelativeAMFCapacity

CRITICALITY ignore TYPE RelativeAMFCapacity

PRESENCE mandatory
}|

{ ID id-PLMNSupportList

CRITICALITY reject TYPE PLMNSupportList

PRESENCE mandatory
}|

{ ID id-CriticalityDiagnostics
CRITICALITY ignore TYPE CriticalityDiagnostics
PRESENCE optional
}|

{ ID id-UERetentionInformation
CRITICALITY ignore TYPE UERetentionInformation
PRESENCE optional
}|

{ ID id-IAB-Supported

CRITICALITY ignore TYPE IAB-Supported

PRESENCE optional
}|

{ ID id-Extended-AMFName

CRITICALITY ignore TYPE Extended-AMFName

PRESENCE optional
}|

{ ID id-MobileIAB-Supported

CRITICALITY ignore TYPE MobileIAB-Supported
PRESENCE optional
}|

{ ID id-AIOTFIdentifier

CRITICALITY reject TYPE AIOTFIdentifier

PRESENCE optional
}|

{ ID id-AIOTFName

CRITICALITY reject TYPE AIOTFName

PRESENCE optional
},

...
}

-- **************************************************************
--
-- NG SETUP FAILURE
--
-- **************************************************************

NGSetupFailure ::= SEQUENCE {

protocolIEs
ProtocolIE-Container

{ {NGSetupFailureIEs} },

...
}

NGSetupFailureIEs NGAP-PROTOCOL-IES ::= {

{ ID id-Cause

CRITICALITY ignore TYPE Cause

PRESENCE mandatory
}|

{ ID id-TimeToWait

CRITICALITY ignore TYPE TimeToWait

PRESENCE optional
}|

{ ID id-CriticalityDiagnostics
CRITICALITY ignore TYPE CriticalityDiagnostics
PRESENCE optional
},

...
}

-- **************************************************************
--
-- RAN Configuration Update Elementary Procedure
--
-- **************************************************************

-- **************************************************************
--
-- RAN CONFIGURATION UPDATE
--
-- **************************************************************

RANConfigurationUpdate ::= SEQUENCE {

protocolIEs
ProtocolIE-Container

{ {RANConfigurationUpdateIEs} },

...
}

RANConfigurationUpdateIEs NGAP-PROTOCOL-IES ::= {

{ ID id-RANNodeName

CRITICALITY ignore TYPE RANNodeName

PRESENCE optional }|

{ ID id-SupportedTAList

CRITICALITY reject TYPE SupportedTAList

PRESENCE optional }|

{ ID id-DefaultPagingDRX

CRITICALITY ignore TYPE PagingDRX

PRESENCE optional }|

{ ID id-GlobalRANNodeID

CRITICALITY ignore TYPE GlobalRANNodeID

PRESENCE optional }|

{ ID id-NGRAN-TNLAssociationToRemoveList

CRITICALITY reject TYPE NGRAN-TNLAssociationToRemoveList

PRESENCE optional }|

{ ID id-NB-IoT-DefaultPagingDRX

CRITICALITY ignore TYPE NB-IoT-DefaultPagingDRX

PRESENCE optional }|

{ ID id-Extended-RANNodeName

CRITICALITY ignore TYPE Extended-RANNodeName

PRESENCE optional }|

{ ID id-AdditionalULI

CRITICALITY ignore TYPE AdditionalULI

PRESENCE optional }|

{ ID id-AIoT-Support

CRITICALITY reject TYPE AIoT-Support

PRESENCE optional },

...
}

-- **************************************************************
--
-- RAN CONFIGURATION UPDATE ACKNOWLEDGE
--
-- **************************************************************

RANConfigurationUpdateAcknowledge ::= SEQUENCE {

protocolIEs
ProtocolIE-Container

{ {RANConfigurationUpdateAcknowledgeIEs} },

...
}

RANConfigurationUpdateAcknowledgeIEs NGAP-PROTOCOL-IES ::= {

{ ID id-CriticalityDiagnostics
CRITICALITY ignore TYPE CriticalityDiagnostics
PRESENCE optional
},

...
}

-- **************************************************************
--
-- RAN CONFIGURATION UPDATE FAILURE
--
-- **************************************************************

RANConfigurationUpdateFailure ::= SEQUENCE {

protocolIEs
ProtocolIE-Container

{ {RANConfigurationUpdateFailureIEs} },

...
}

RANConfigurationUpdateFailureIEs NGAP-PROTOCOL-IES ::= {

{ ID id-Cause

CRITICALITY ignore TYPE Cause

PRESENCE mandatory
}|

{ ID id-TimeToWait

CRITICALITY ignore TYPE TimeToWait

PRESENCE optional
}|

{ ID id-CriticalityDiagnostics
CRITICALITY ignore TYPE CriticalityDiagnostics
PRESENCE optional
},
...
}

-- **************************************************************
--
-- AMF Configuration Update Elementary Procedure
--
-- **************************************************************

-- **************************************************************
--
-- AMF CONFIGURATION UPDATE
--
-- **************************************************************

AMFConfigurationUpdate ::= SEQUENCE {

protocolIEs
ProtocolIE-Container

{ {AMFConfigurationUpdateIEs} },

...
}

AMFConfigurationUpdateIEs NGAP-PROTOCOL-IES ::= {

{ ID id-AMFName

CRITICALITY reject TYPE AMFName

PRESENCE optional
}|

{ ID id-ServedGUAMIList

CRITICALITY reject TYPE ServedGUAMIList

PRESENCE optional
}|

{ ID id-RelativeAMFCapacity

CRITICALITY ignore TYPE RelativeAMFCapacity

PRESENCE optional
}|

{ ID id-PLMNSupportList

CRITICALITY reject TYPE PLMNSupportList

PRESENCE optional
}|

{ ID id-AMF-TNLAssociationToAddList

CRITICALITY ignore TYPE AMF-TNLAssociationToAddList

PRESENCE optional
}|

{ ID id-AMF-TNLAssociationToRemoveList
CRITICALITY ignore TYPE AMF-TNLAssociationToRemoveList
PRESENCE optional
}|

{ ID id-AMF-TNLAssociationToUpdateList
CRITICALITY ignore TYPE AMF-TNLAssociationToUpdateList
PRESENCE optional
}|

{ ID id-Extended-AMFName

CRITICALITY ignore TYPE Extended-AMFName

PRESENCE optional
},

...
}

-- **************************************************************
--
-- AMF CONFIGURATION UPDATE ACKNOWLEDGE
--
-- **************************************************************

AMFConfigurationUpdateAcknowledge ::= SEQUENCE {

protocolIEs
ProtocolIE-Container

{ {AMFConfigurationUpdateAcknowledgeIEs} },

...
}

AMFConfigurationUpdateAcknowledgeIEs NGAP-PROTOCOL-IES ::= {

{ ID id-AMF-TNLAssociationSetupList

CRITICALITY ignore TYPE AMF-TNLAssociationSetupList

PRESENCE optional
}|

{ ID id-AMF-TNLAssociationFailedToSetupList
CRITICALITY ignore TYPE TNLAssociationList

PRESENCE optional
}|

{ ID id-CriticalityDiagnostics

CRITICALITY ignore TYPE CriticalityDiagnostics

PRESENCE optional
},

...
}

-- **************************************************************
--
-- AMF CONFIGURATION UPDATE FAILURE
--
-- **************************************************************

AMFConfigurationUpdateFailure ::= SEQUENCE {

protocolIEs
ProtocolIE-Container

{ {AMFConfigurationUpdateFailureIEs} },

...
}

AMFConfigurationUpdateFailureIEs NGAP-PROTOCOL-IES ::= {

{ ID id-Cause

CRITICALITY ignore TYPE Cause

PRESENCE mandatory
}|

{ ID id-TimeToWait

CRITICALITY ignore TYPE TimeToWait

PRESENCE optional
}|

{ ID id-CriticalityDiagnostics
CRITICALITY ignore TYPE CriticalityDiagnostics
PRESENCE optional
},

...
}

-- **************************************************************
--
-- AMF Status Indication Elementary Procedure
--
-- **************************************************************

-- **************************************************************
--
-- AMF STATUS INDICATION
--
-- **************************************************************

AMFStatusIndication ::= SEQUENCE {

protocolIEs
ProtocolIE-Container

{ {AMFStatusIndicationIEs} },

...
}

AMFStatusIndicationIEs NGAP-PROTOCOL-IES ::= {

{ ID id-UnavailableGUAMIList

CRITICALITY reject TYPE UnavailableGUAMIList

PRESENCE mandatory
},

...
}

-- **************************************************************
--
-- NG Reset Elementary Procedure
--
-- **************************************************************

-- **************************************************************
--

-- NG RESET
--
-- **************************************************************

NGReset ::= SEQUENCE {

protocolIEs
ProtocolIE-Container

{ {NGResetIEs} },

...
}

NGResetIEs NGAP-PROTOCOL-IES ::= {

{ ID id-Cause

CRITICALITY ignore TYPE Cause

PRESENCE mandatory
}|

{ ID id-ResetType

CRITICALITY reject TYPE ResetType

PRESENCE mandatory
},

...
}

-- **************************************************************
--
-- NG RESET ACKNOWLEDGE
--
-- **************************************************************

NGResetAcknowledge ::= SEQUENCE {

protocolIEs
ProtocolIE-Container

{ {NGResetAcknowledgeIEs} },

...
}

NGResetAcknowledgeIEs NGAP-PROTOCOL-IES ::= {

{ ID id-UE-associatedLogicalNG-connectionList

CRITICALITY ignore TYPE UE-associatedLogicalNG-connectionList

PRESENCE optional

}|

{ ID id-CriticalityDiagnostics

CRITICALITY ignore TYPE CriticalityDiagnostics

PRESENCE optional

},

...
}

-- **************************************************************
--
-- Error Indication Elementary Procedure
--
-- **************************************************************

-- **************************************************************
--
-- ERROR INDICATION
--
-- **************************************************************

ErrorIndication ::= SEQUENCE {

protocolIEs
ProtocolIE-Container

{ {ErrorIndicationIEs} },

...
}

ErrorIndicationIEs NGAP-PROTOCOL-IES ::= {

{ ID id-AMF-UE-NGAP-ID

CRITICALITY ignore TYPE AMF-UE-NGAP-ID

PRESENCE optional
}|

{ ID id-RAN-UE-NGAP-ID

CRITICALITY ignore TYPE RAN-UE-NGAP-ID

PRESENCE optional
}|

{ ID id-Cause

CRITICALITY ignore TYPE Cause

PRESENCE optional
}|

{ ID id-CriticalityDiagnostics
CRITICALITY ignore TYPE CriticalityDiagnostics
PRESENCE optional
}|

{ ID id-FiveG-S-TMSI

CRITICALITY ignore TYPE FiveG-S-TMSI

PRESENCE optional
},

...
}

-- **************************************************************
--
-- OVERLOAD START
--
-- **************************************************************

OverloadStart ::= SEQUENCE {

protocolIEs
ProtocolIE-Container

{ {OverloadStartIEs} },

...
}

OverloadStartIEs NGAP-PROTOCOL-IES ::= {

{ ID id-AMFOverloadResponse

CRITICALITY reject TYPE OverloadResponse

PRESENCE optional
}|

{ ID id-AMFTrafficLoadReductionIndication

CRITICALITY ignore TYPE TrafficLoadReductionIndication

PRESENCE optional
}|

{ ID id-OverloadStartNSSAIList

CRITICALITY ignore TYPE OverloadStartNSSAIList

PRESENCE optional
}|

{ ID id-GUAMIList

CRITICALITY ignore TYPE GUAMIList

PRESENCE optional
},

...
}

-- **************************************************************
--
-- OVERLOAD STOP
--
-- **************************************************************

OverloadStop ::= SEQUENCE {

protocolIEs
ProtocolIE-Container

{ {OverloadStopIEs} },

...
}

OverloadStopIEs NGAP-PROTOCOL-IES ::= {

{ ID id-GUAMIList

CRITICALITY ignore TYPE GUAMIList
PRESENCE optional

},

...
}

-- **************************************************************
--
-- CONFIGURATION TRANSFER ELEMENTARY PROCEDURES
--
-- **************************************************************

-- **************************************************************
--
-- UPLINK RAN CONFIGURATION TRANSFER
--
-- **************************************************************

UplinkRANConfigurationTransfer ::= SEQUENCE {

protocolIEs
ProtocolIE-Container

{ {UplinkRANConfigurationTransferIEs} },

...
}

UplinkRANConfigurationTransferIEs NGAP-PROTOCOL-IES ::= {

{ ID id-SONConfigurationTransferUL

CRITICALITY ignore TYPE SONConfigurationTransfer

PRESENCE optional
}|

{ ID id-ENDC-SONConfigurationTransferUL

CRITICALITY ignore TYPE EN-DCSONConfigurationTransfer

PRESENCE optional
}|

{ ID id-IntersystemSONConfigurationTransferUL

CRITICALITY ignore TYPE IntersystemSONConfigurationTransfer
PRESENCE optional
},

...
}

-- **************************************************************
--
-- DOWNLINK RAN CONFIGURATION TRANSFER
--
-- **************************************************************

DownlinkRANConfigurationTransfer ::= SEQUENCE {

protocolIEs
ProtocolIE-Container

{ {DownlinkRANConfigurationTransferIEs} },

...
}

DownlinkRANConfigurationTransferIEs NGAP-PROTOCOL-IES ::= {

{ ID id-SONConfigurationTransferDL

CRITICALITY ignore TYPE SONConfigurationTransfer

PRESENCE optional
}|

{ ID id-ENDC-SONConfigurationTransferDL

CRITICALITY ignore TYPE EN-DCSONConfigurationTransfer

PRESENCE optional
}|

{ ID id-IntersystemSONConfigurationTransferDL

CRITICALITY ignore TYPE IntersystemSONConfigurationTransfer
PRESENCE optional
},

...
}

-- **************************************************************
--
-- WARNING MESSAGE TRANSMISSION ELEMENTARY PROCEDURES
--
-- **************************************************************

-- **************************************************************
--
-- Write-Replace Warning Elementary Procedure
--
-- **************************************************************

-- **************************************************************
--
-- WRITE-REPLACE WARNING REQUEST
--
-- **************************************************************

WriteReplaceWarningRequest ::= SEQUENCE {

protocolIEs
ProtocolIE-Container

{ {WriteReplaceWarningRequestIEs} },

...
}

WriteReplaceWarningRequestIEs NGAP-PROTOCOL-IES ::= {

{ ID id-MessageIdentifier

CRITICALITY reject TYPE MessageIdentifier

PRESENCE mandatory
}|

{ ID id-SerialNumber

CRITICALITY reject TYPE SerialNumber

PRESENCE mandatory
}|

{ ID id-WarningAreaList

CRITICALITY ignore TYPE WarningAreaList

PRESENCE optional
}|

{ ID id-RepetitionPeriod

CRITICALITY reject TYPE RepetitionPeriod

PRESENCE mandatory
}|

{ ID id-NumberOfBroadcastsRequested
CRITICALITY reject TYPE NumberOfBroadcastsRequested
PRESENCE mandatory
}|

{ ID id-WarningType

CRITICALITY ignore TYPE WarningType

PRESENCE optional
}|

{ ID id-WarningSecurityInfo

CRITICALITY ignore TYPE WarningSecurityInfo

PRESENCE optional
}|

{ ID id-DataCodingScheme

CRITICALITY ignore TYPE DataCodingScheme

PRESENCE optional
}|

{ ID id-WarningMessageContents

CRITICALITY ignore TYPE WarningMessageContents

PRESENCE optional
}|

{ ID id-ConcurrentWarningMessageInd
CRITICALITY reject TYPE ConcurrentWarningMessageInd
PRESENCE optional
}|

{ ID id-WarningAreaCoordinates

CRITICALITY ignore TYPE WarningAreaCoordinates

PRESENCE optional
},

...
}

-- **************************************************************
--
-- WRITE-REPLACE WARNING RESPONSE
--
-- **************************************************************

WriteReplaceWarningResponse ::= SEQUENCE {

protocolIEs

ProtocolIE-Container

{ {WriteReplaceWarningResponseIEs} },

...
}

WriteReplaceWarningResponseIEs NGAP-PROTOCOL-IES ::= {

{ ID id-MessageIdentifier

CRITICALITY reject TYPE MessageIdentifier

PRESENCE mandatory
}|

{ ID id-SerialNumber

CRITICALITY reject TYPE SerialNumber

PRESENCE mandatory
}|

{ ID id-BroadcastCompletedAreaList
CRITICALITY ignore TYPE BroadcastCompletedAreaList
PRESENCE optional
}|

{ ID id-CriticalityDiagnostics

CRITICALITY ignore TYPE CriticalityDiagnostics

PRESENCE optional
},

...
}

-- **************************************************************
--
-- PWS Cancel Elementary Procedure
--
-- **************************************************************

-- **************************************************************
--
-- PWS CANCEL REQUEST
--
-- **************************************************************

PWSCancelRequest ::= SEQUENCE {

protocolIEs
ProtocolIE-Container

{ {PWSCancelRequestIEs} },

...
}

PWSCancelRequestIEs NGAP-PROTOCOL-IES ::= {

{ ID id-MessageIdentifier

CRITICALITY reject TYPE MessageIdentifier

PRESENCE mandatory }|

{ ID id-SerialNumber

CRITICALITY reject TYPE SerialNumber

PRESENCE mandatory }|

{ ID id-WarningAreaList

CRITICALITY ignore TYPE WarningAreaList

PRESENCE optional
}|

{ ID id-CancelAllWarningMessages
CRITICALITY reject TYPE CancelAllWarningMessages

PRESENCE optional
},

...
}

-- **************************************************************
--
-- PWS CANCEL RESPONSE
--
-- **************************************************************

PWSCancelResponse ::= SEQUENCE {

protocolIEs
ProtocolIE-Container

{ {PWSCancelResponseIEs} },

...
}

PWSCancelResponseIEs NGAP-PROTOCOL-IES ::= {

{ ID id-MessageIdentifier

CRITICALITY reject TYPE MessageIdentifier

PRESENCE mandatory }|

{ ID id-SerialNumber

CRITICALITY reject TYPE SerialNumber

PRESENCE mandatory }|

{ ID id-BroadcastCancelledAreaList CRITICALITY ignore TYPE BroadcastCancelledAreaList
PRESENCE optional
}|

{ ID id-CriticalityDiagnostics
CRITICALITY ignore TYPE CriticalityDiagnostics

PRESENCE optional
},

...
}

-- **************************************************************
--
-- PWS Restart Indication Elementary Procedure
--
-- **************************************************************

-- **************************************************************
--
-- PWS RESTART INDICATION
--
-- **************************************************************

PWSRestartIndication ::= SEQUENCE {

protocolIEs
ProtocolIE-Container

{ {PWSRestartIndicationIEs} },

...
}

PWSRestartIndicationIEs NGAP-PROTOCOL-IES ::= {

{ ID id-CellIDListForRestart

CRITICALITY reject TYPE CellIDListForRestart

PRESENCE mandatory
}|

{ ID id-GlobalRANNodeID

CRITICALITY reject TYPE GlobalRANNodeID

PRESENCE mandatory
}|

{ ID id-TAIListForRestart

CRITICALITY reject TYPE TAIListForRestart

PRESENCE mandatory
}|

{ ID id-EmergencyAreaIDListForRestart
CRITICALITY reject TYPE EmergencyAreaIDListForRestart
PRESENCE optional
},

...
}

-- **************************************************************
--
-- PWS Failure Indication Elementary Procedure
--
-- **************************************************************

-- **************************************************************

--
-- PWS FAILURE INDICATION
--
-- **************************************************************

PWSFailureIndication ::= SEQUENCE {

protocolIEs
ProtocolIE-Container

{ {PWSFailureIndicationIEs} },

...
}

PWSFailureIndicationIEs NGAP-PROTOCOL-IES ::= {

{ ID id-PWSFailedCellIDList

CRITICALITY reject TYPE PWSFailedCellIDList
PRESENCE mandatory }|

{ ID id-GlobalRANNodeID

CRITICALITY reject TYPE GlobalRANNodeID

PRESENCE mandatory },

...
}

-- **************************************************************
--
-- NRPPA TRANSPORT ELEMENTARY PROCEDURES
--
-- **************************************************************

-- **************************************************************
--
-- DOWNLINK UE ASSOCIATED NRPPA TRANSPORT
--
-- **************************************************************

DownlinkUEAssociatedNRPPaTransport ::= SEQUENCE {

protocolIEs
ProtocolIE-Container

{ {DownlinkUEAssociatedNRPPaTransportIEs} },

...
}

DownlinkUEAssociatedNRPPaTransportIEs NGAP-PROTOCOL-IES ::= {

{ ID id-AMF-UE-NGAP-ID

CRITICALITY reject TYPE AMF-UE-NGAP-ID

PRESENCE mandatory }|

{ ID id-RAN-UE-NGAP-ID

CRITICALITY reject TYPE RAN-UE-NGAP-ID

PRESENCE mandatory }|

{ ID id-RoutingID

CRITICALITY reject TYPE RoutingID

PRESENCE mandatory }|

{ ID id-NRPPa-PDU

CRITICALITY reject TYPE NRPPa-PDU

PRESENCE mandatory },

...
}

-- **************************************************************
--
-- UPLINK UE ASSOCIATED NRPPA TRANSPORT
--
-- **************************************************************

UplinkUEAssociatedNRPPaTransport ::= SEQUENCE {

protocolIEs
ProtocolIE-Container

{ {UplinkUEAssociatedNRPPaTransportIEs} },

...
}

UplinkUEAssociatedNRPPaTransportIEs NGAP-PROTOCOL-IES ::= {

{ ID id-AMF-UE-NGAP-ID

CRITICALITY reject TYPE AMF-UE-NGAP-ID

PRESENCE mandatory }|

{ ID id-RAN-UE-NGAP-ID

CRITICALITY reject TYPE RAN-UE-NGAP-ID

PRESENCE mandatory }|

{ ID id-RoutingID

CRITICALITY reject TYPE RoutingID

PRESENCE mandatory }|

{ ID id-NRPPa-PDU

CRITICALITY reject TYPE NRPPa-PDU

PRESENCE mandatory },

...
}

-- **************************************************************
--
-- DOWNLINK NON UE ASSOCIATED NRPPA TRANSPORT
--
-- **************************************************************

DownlinkNonUEAssociatedNRPPaTransport ::= SEQUENCE {

protocolIEs
ProtocolIE-Container

{ {DownlinkNonUEAssociatedNRPPaTransportIEs} },

...
}

DownlinkNonUEAssociatedNRPPaTransportIEs NGAP-PROTOCOL-IES ::= {

{ ID id-RoutingID

CRITICALITY reject TYPE RoutingID

PRESENCE mandatory }|

{ ID id-NRPPa-PDU

CRITICALITY reject TYPE NRPPa-PDU

PRESENCE mandatory },

...
}

-- **************************************************************
--
-- UPLINK NON UE ASSOCIATED NRPPA TRANSPORT
--
-- **************************************************************

UplinkNonUEAssociatedNRPPaTransport ::= SEQUENCE {

protocolIEs
ProtocolIE-Container

{ {UplinkNonUEAssociatedNRPPaTransportIEs} },

...
}

UplinkNonUEAssociatedNRPPaTransportIEs NGAP-PROTOCOL-IES ::= {

{ ID id-RoutingID

CRITICALITY reject TYPE RoutingID

PRESENCE mandatory }|

{ ID id-NRPPa-PDU

CRITICALITY reject TYPE NRPPa-PDU

PRESENCE mandatory },

...
}

-- **************************************************************
--
-- TRACE ELEMENTARY PROCEDURES
--
-- **************************************************************

-- **************************************************************
--
-- TRACE START
--
-- **************************************************************

TraceStart ::= SEQUENCE {

protocolIEs
ProtocolIE-Container

{ {TraceStartIEs} },

...
}

TraceStartIEs NGAP-PROTOCOL-IES ::= {

{ ID id-AMF-UE-NGAP-ID

CRITICALITY reject TYPE AMF-UE-NGAP-ID

PRESENCE mandatory
}|

{ ID id-RAN-UE-NGAP-ID

CRITICALITY reject TYPE RAN-UE-NGAP-ID

PRESENCE mandatory
}|

{ ID id-TraceActivation

CRITICALITY ignore TYPE TraceActivation

PRESENCE mandatory
},

...
}

-- **************************************************************
--
-- TRACE FAILURE INDICATION
--
-- **************************************************************

TraceFailureIndication ::= SEQUENCE {

protocolIEs
ProtocolIE-Container

{ {TraceFailureIndicationIEs} },

...
}

TraceFailureIndicationIEs NGAP-PROTOCOL-IES ::= {

{ ID id-AMF-UE-NGAP-ID

CRITICALITY reject TYPE AMF-UE-NGAP-ID

PRESENCE mandatory
}|

{ ID id-RAN-UE-NGAP-ID

CRITICALITY reject TYPE RAN-UE-NGAP-ID

PRESENCE mandatory
}|

{ ID id-NGRANTraceID

CRITICALITY ignore TYPE NGRANTraceID

PRESENCE mandatory
}|

{ ID id-Cause

CRITICALITY ignore TYPE Cause

PRESENCE mandatory
},

...
}

-- **************************************************************
--
-- DEACTIVATE TRACE
--
-- **************************************************************

DeactivateTrace ::= SEQUENCE {

protocolIEs
ProtocolIE-Container

{ {DeactivateTraceIEs} },

...
}

DeactivateTraceIEs NGAP-PROTOCOL-IES ::= {

{ ID id-AMF-UE-NGAP-ID

CRITICALITY reject TYPE AMF-UE-NGAP-ID

PRESENCE mandatory
}|

{ ID id-RAN-UE-NGAP-ID

CRITICALITY reject TYPE RAN-UE-NGAP-ID

PRESENCE mandatory
}|

{ ID id-NGRANTraceID

CRITICALITY ignore TYPE NGRANTraceID

PRESENCE mandatory
},

...
}

-- **************************************************************
--
-- CELL TRAFFIC TRACE
--
-- **************************************************************

CellTrafficTrace ::= SEQUENCE {

protocolIEs
ProtocolIE-Container

{ {CellTrafficTraceIEs} },

...
}

CellTrafficTraceIEs NGAP-PROTOCOL-IES ::= {

{ID id-AMF-UE-NGAP-ID

CRITICALITY reject TYPE AMF-UE-NGAP-ID

PRESENCE mandatory }|

{ID id-RAN-UE-NGAP-ID

CRITICALITY reject TYPE RAN-UE-NGAP-ID

PRESENCE mandatory }|

{ID id-NGRANTraceID

CRITICALITY ignore TYPE NGRANTraceID

PRESENCE mandatory }|

{ID id-NGRAN-CGI

CRITICALITY ignore TYPE NGRAN-CGI

PRESENCE mandatory }|

{ID id-TraceCollectionEntityIPAddress
CRITICALITY ignore TYPE TransportLayerAddress
PRESENCE mandatory }|

{ID id-PrivacyIndicator

CRITICALITY ignore TYPE PrivacyIndicator

PRESENCE optional
}|

{ID id-TraceCollectionEntityURI

CRITICALITY ignore TYPE URI-address

PRESENCE optional
},

...
}

-- **************************************************************
--
-- LOCATION REPORTING ELEMENTARY PROCEDURES
--
-- **************************************************************

-- **************************************************************
--
-- LOCATION REPORTING CONTROL
--
-- **************************************************************

LocationReportingControl ::= SEQUENCE {

protocolIEs

ProtocolIE-Container

{ {LocationReportingControlIEs} },

...
}

LocationReportingControlIEs NGAP-PROTOCOL-IES ::= {

{ ID id-AMF-UE-NGAP-ID

CRITICALITY reject TYPE AMF-UE-NGAP-ID

PRESENCE mandatory
}|

{ ID id-RAN-UE-NGAP-ID

CRITICALITY reject TYPE RAN-UE-NGAP-ID

PRESENCE mandatory
}|

{ ID id-LocationReportingRequestType
CRITICALITY ignore TYPE LocationReportingRequestType
PRESENCE mandatory
},

...
}

-- **************************************************************
--
-- LOCATION REPORTING FAILURE INDICATION
--
-- **************************************************************

LocationReportingFailureIndication ::= SEQUENCE {

protocolIEs

ProtocolIE-Container

{ {LocationReportingFailureIndicationIEs} },

...
}

LocationReportingFailureIndicationIEs NGAP-PROTOCOL-IES ::= {

{ ID id-AMF-UE-NGAP-ID

CRITICALITY reject TYPE AMF-UE-NGAP-ID

PRESENCE mandatory }|

{ ID id-RAN-UE-NGAP-ID

CRITICALITY reject TYPE RAN-UE-NGAP-ID

PRESENCE mandatory }|

{ ID id-Cause

CRITICALITY ignore TYPE Cause

PRESENCE mandatory }|

{ ID id-Aerial-UE-FlightInformationOngoingReporting-failed

CRITICALITY ignore TYPE Aerial-UE-FlightInformationOngoingReporting-failed

PRESENCE optional},

...
}

Aerial-UE-FlightInformationOngoingReporting-failed::= ENUMERATED {

true,

...
}

-- **************************************************************
--
-- LOCATION REPORT
--
-- **************************************************************

LocationReport ::= SEQUENCE {

protocolIEs

ProtocolIE-Container

{ {LocationReportIEs} },

...
}

LocationReportIEs NGAP-PROTOCOL-IES ::= {

{ ID id-AMF-UE-NGAP-ID

CRITICALITY reject TYPE AMF-UE-NGAP-ID

PRESENCE mandatory
}|

{ ID id-RAN-UE-NGAP-ID

CRITICALITY reject TYPE RAN-UE-NGAP-ID

PRESENCE mandatory
}|

{ ID id-UserLocationInformation

CRITICALITY ignore TYPE UserLocationInformation

PRESENCE mandatory
}|

{ ID id-UEPresenceInAreaOfInterestList
CRITICALITY ignore TYPE UEPresenceInAreaOfInterestList
PRESENCE optional
}|

{ ID id-LocationReportingRequestType

CRITICALITY ignore TYPE LocationReportingRequestType

PRESENCE mandatory
},

...
}

-- **************************************************************
--
-- UE TNLA BINDING ELEMENTARY PROCEDURES
--
-- **************************************************************

-- **************************************************************
--
-- UE TNLA BINDING RELEASE REQUEST
--
-- **************************************************************

UETNLABindingReleaseRequest ::= SEQUENCE {

protocolIEs

ProtocolIE-Container

{ {UETNLABindingReleaseRequestIEs} },

...
}

UETNLABindingReleaseRequestIEs NGAP-PROTOCOL-IES ::= {

{ ID id-AMF-UE-NGAP-ID
CRITICALITY reject TYPE AMF-UE-NGAP-ID
PRESENCE mandatory }|

{ ID id-RAN-UE-NGAP-ID
CRITICALITY reject TYPE RAN-UE-NGAP-ID
PRESENCE mandatory },

...
}

-- **************************************************************
--
-- UE RADIO CAPABILITY MANAGEMENT ELEMENTARY PROCEDURES
--
-- **************************************************************

-- **************************************************************
--
-- UE RADIO CAPABILITY INFO INDICATION
--
-- **************************************************************

UERadioCapabilityInfoIndication ::= SEQUENCE {

protocolIEs

ProtocolIE-Container

{ {UERadioCapabilityInfoIndicationIEs} },

...
}

UERadioCapabilityInfoIndicationIEs NGAP-PROTOCOL-IES ::= {

{ ID id-AMF-UE-NGAP-ID

CRITICALITY reject TYPE AMF-UE-NGAP-ID

 PRESENCE mandatory
}|

{ ID id-RAN-UE-NGAP-ID

CRITICALITY reject TYPE RAN-UE-NGAP-ID

 PRESENCE mandatory
}|

{ ID id-UERadioCapability

CRITICALITY ignore TYPE UERadioCapability

 PRESENCE mandatory
}|

{ ID id-UERadioCapabilityForPaging
CRITICALITY ignore TYPE UERadioCapabilityForPaging  PRESENCE optional
}|

{ ID id-UERadioCapability-EUTRA-Format CRITICALITY ignore TYPE UERadioCapability

 PRESENCE optional
}|

{ ID id-XrDeviceWith2Rx

CRITICALITY ignore TYPE XrDeviceWith2Rx

 PRESENCE optional
},

...
}

-- **************************************************************
--
-- UE Radio Capability Check Elementary Procedure
--
-- **************************************************************

-- **************************************************************
--
-- UE RADIO CAPABILITY CHECK REQUEST
--
-- **************************************************************

UERadioCapabilityCheckRequest ::= SEQUENCE {

protocolIEs
ProtocolIE-Container

{ {UERadioCapabilityCheckRequestIEs} },

...
}

UERadioCapabilityCheckRequestIEs NGAP-PROTOCOL-IES ::= {

{ ID id-AMF-UE-NGAP-ID

CRITICALITY reject TYPE AMF-UE-NGAP-ID

PRESENCE mandatory }|

{ ID id-RAN-UE-NGAP-ID

CRITICALITY reject TYPE RAN-UE-NGAP-ID

PRESENCE mandatory }|

{ ID id-UERadioCapability

CRITICALITY ignore TYPE UERadioCapability
PRESENCE optional
}|

{ ID id-UERadioCapabilityID
CRITICALITY reject TYPE UERadioCapabilityID
PRESENCE optional
},

...
}

-- **************************************************************
--

-- UE RADIO CAPABILITY CHECK RESPONSE
--
-- **************************************************************

UERadioCapabilityCheckResponse ::= SEQUENCE {

protocolIEs
ProtocolIE-Container

{ {UERadioCapabilityCheckResponseIEs} },

...
}

UERadioCapabilityCheckResponseIEs NGAP-PROTOCOL-IES ::= {

{ ID id-AMF-UE-NGAP-ID

CRITICALITY ignore TYPE AMF-UE-NGAP-ID

 PRESENCE mandatory
}|

{ ID id-RAN-UE-NGAP-ID

CRITICALITY ignore TYPE RAN-UE-NGAP-ID

 PRESENCE mandatory
}|

{ ID id-IMSVoiceSupportIndicator

CRITICALITY reject TYPE IMSVoiceSupportIndicator
 PRESENCE mandatory
}|

{ ID id-CriticalityDiagnostics

CRITICALITY ignore TYPE CriticalityDiagnostics
 PRESENCE optional
},

...
}

-- **************************************************************
--
-- PRIVATE MESSAGE ELEMENTARY PROCEDURE
--
-- **************************************************************

-- **************************************************************
--
-- PRIVATE MESSAGE
--
-- **************************************************************

PrivateMessage ::= SEQUENCE {

privateIEs
PrivateIE-Container
{ { PrivateMessageIEs } },

...
}

PrivateMessageIEs NGAP-PRIVATE-IES ::= {

...
}

-- **************************************************************
--
-- DATA USAGE REPORTING ELEMENTARY PROCEDURES
--
-- **************************************************************

-- **************************************************************
--
-- SECONDARY RAT DATA USAGE REPORT
--
-- **************************************************************

SecondaryRATDataUsageReport ::= SEQUENCE {

protocolIEs
ProtocolIE-Container

{ {SecondaryRATDataUsageReportIEs} },

...

}

SecondaryRATDataUsageReportIEs NGAP-PROTOCOL-IES ::= {

{ ID id-AMF-UE-NGAP-ID

CRITICALITY ignore TYPE AMF-UE-NGAP-ID

PRESENCE mandatory

}|

{ ID id-RAN-UE-NGAP-ID

CRITICALITY ignore TYPE RAN-UE-NGAP-ID

PRESENCE mandatory

}|

{ ID id-PDUSessionResourceSecondaryRATUsageList
CRITICALITY ignore TYPE PDUSessionResourceSecondaryRATUsageList

PRESENCE mandatory

}|

{ ID id-HandoverFlag

CRITICALITY ignore TYPE HandoverFlag

PRESENCE optional

}|

{ ID id-UserLocationInformation

CRITICALITY ignore TYPE UserLocationInformation

PRESENCE optional

},

...
}

-- **************************************************************
--
-- RIM INFORMATION TRANSFER ELEMENTARY PROCEDURES
--
-- **************************************************************

-- **************************************************************
--
-- UPLINK RIM INFORMATION TRANSFER
--
-- **************************************************************

UplinkRIMInformationTransfer ::= SEQUENCE {

protocolIEs
ProtocolIE-Container

{ {UplinkRIMInformationTransferIEs} },

...
}

UplinkRIMInformationTransferIEs NGAP-PROTOCOL-IES ::= {

{ ID id-RIMInformationTransfer CRITICALITY ignore TYPE RIMInformationTransfer PRESENCE optional
},

...
}

-- **************************************************************
--
-- DOWNLINK RIM INFORMATION TRANSFER
--
-- **************************************************************

DownlinkRIMInformationTransfer ::= SEQUENCE {

protocolIEs
ProtocolIE-Container

{ {DownlinkRIMInformationTransferIEs} },

...
}

DownlinkRIMInformationTransferIEs NGAP-PROTOCOL-IES ::= {

{ ID id-RIMInformationTransfer CRITICALITY ignore TYPE RIMInformationTransfer PRESENCE optional
},

...
}

-- **************************************************************
--
-- Connection Establishment Indication
--
-- **************************************************************

ConnectionEstablishmentIndication::= SEQUENCE {

protocolIEs

ProtocolIE-Container { {ConnectionEstablishmentIndicationIEs} },

...
}

ConnectionEstablishmentIndicationIEs NGAP-PROTOCOL-IES ::= {

{ ID id-AMF-UE-NGAP-ID

CRITICALITY reject TYPE AMF-UE-NGAP-ID

 PRESENCE mandatory
}|

{ ID id-RAN-UE-NGAP-ID

CRITICALITY reject TYPE RAN-UE-NGAP-ID

 PRESENCE mandatory
}|

{ ID id-UERadioCapability

CRITICALITY ignore TYPE UERadioCapability

 PRESENCE optional
}|

{ ID id-EndIndication

CRITICALITY ignore TYPE EndIndication

 PRESENCE optional
}|

{ ID id-S-NSSAI

CRITICALITY ignore TYPE S-NSSAI

 PRESENCE optional
}|

{ ID id-AllowedNSSAI

CRITICALITY ignore TYPE AllowedNSSAI

 PRESENCE optional
}|

{ ID id-UE-DifferentiationInfo

CRITICALITY ignore TYPE UE-DifferentiationInfo
 PRESENCE optional
}|

{ ID id-DL-CP-SecurityInformation

CRITICALITY ignore TYPE DL-CP-SecurityInformation  PRESENCE optional
}|

{ ID id-NB-IoT-UEPriority

CRITICALITY ignore TYPE NB-IoT-UEPriority

 PRESENCE optional
}|

{ ID id-Enhanced-CoverageRestriction
CRITICALITY ignore TYPE Enhanced-CoverageRestriction PRESENCE optional
}|

{ ID id-CEmodeBrestricted

CRITICALITY ignore TYPE CEmodeBrestricted

 PRESENCE optional
}|

{ ID id-UERadioCapabilityID

CRITICALITY reject TYPE UERadioCapabilityID

 PRESENCE optional
}|

{ ID id-MaskedIMEISV

CRITICALITY ignore TYPE MaskedIMEISV

 PRESENCE optional
}|

{ ID id-OldAMF

CRITICALITY reject TYPE AMFName

 PRESENCE optional
}|

{ ID id-Partially-Allowed-NSSAI

CRITICALITY ignore TYPE Partially-Allowed-NSSAI
 PRESENCE optional
}|

{ ID id-ExtendedOldAMF

CRITICALITY ignore TYPE Extended-AMFName

 PRESENCE optional
},

...
}

-- **************************************************************
--
-- UE RADIO CAPABILITY ID MAPPING ELEMENTARY PROCEDURES
--
-- **************************************************************

-- **************************************************************
--
-- UE RADIO CAPABILITY ID MAPPING REQUEST
--
-- **************************************************************

UERadioCapabilityIDMappingRequest ::= SEQUENCE {

protocolIEs
ProtocolIE-Container

{ {UERadioCapabilityIDMappingRequestIEs} },

...
}

UERadioCapabilityIDMappingRequestIEs NGAP-PROTOCOL-IES ::= {

{ ID id-UERadioCapabilityID
CRITICALITY reject TYPE UERadioCapabilityID
PRESENCE mandatory },

...
}

-- **************************************************************
--
-- UE RADIO CAPABILITY ID MAPPING RESPONSE
--
-- **************************************************************

UERadioCapabilityIDMappingResponse ::= SEQUENCE {

protocolIEs
ProtocolIE-Container

{ {UERadioCapabilityIDMappingResponseIEs} },

...
}

UERadioCapabilityIDMappingResponseIEs NGAP-PROTOCOL-IES ::= {

{ ID id-UERadioCapabilityID

CRITICALITY reject TYPE UERadioCapabilityID

PRESENCE mandatory
}|

{ ID id-UERadioCapability

CRITICALITY ignore TYPE UERadioCapability

PRESENCE mandatory  }|

{ ID id-CriticalityDiagnostics
CRITICALITY ignore TYPE CriticalityDiagnostics
PRESENCE optional
},

...
}

-- **************************************************************
--
-- AMF CP Relocation Indication
--
-- **************************************************************

AMFCPRelocationIndication ::= SEQUENCE {

protocolIEs

ProtocolIE-Container { { AMFCPRelocationIndicationIEs} },

...
}

AMFCPRelocationIndicationIEs NGAP-PROTOCOL-IES ::= {

{ ID id-AMF-UE-NGAP-ID

CRITICALITY reject TYPE AMF-UE-NGAP-ID

PRESENCE mandatory
}|

{ ID id-RAN-UE-NGAP-ID

CRITICALITY reject TYPE RAN-UE-NGAP-ID

PRESENCE mandatory
}|

{ ID id-S-NSSAI

CRITICALITY ignore TYPE S-NSSAI

PRESENCE optional
}| --this IE is not used and
ignored

{ ID id-AllowedNSSAI

CRITICALITY ignore TYPE AllowedNSSAI

PRESENCE optional
}| --this IE is not used and
ignored

{ ID id-Partially-Allowed-NSSAI
CRITICALITY ignore TYPE Partially-Allowed-NSSAI
PRESENCE optional
}, --this IE is not used and
ignored

...
}

-- **************************************************************
--
-- MBS SESSION MANAGEMENT ELEMENTARY PROCEDURES
--
-- **************************************************************

-- **************************************************************
--
-- Broadcast Session Setup Elementary Procedure
--
-- **************************************************************

-- **************************************************************

--
-- BROADCAST SESSION SETUP REQUEST
--
-- **************************************************************

BroadcastSessionSetupRequest ::= SEQUENCE {

protocolIEs
ProtocolIE-Container

{ {BroadcastSessionSetupRequestIEs} },

...
}

BroadcastSessionSetupRequestIEs NGAP-PROTOCOL-IES ::= {

{ ID id-MBS-SessionID

CRITICALITY reject TYPE MBS-SessionID

PRESENCE mandatory
}|

{ ID id-S-NSSAI

CRITICALITY reject TYPE S-NSSAI

PRESENCE mandatory
}|

{ ID id-MBS-ServiceArea

CRITICALITY reject TYPE MBS-ServiceArea

PRESENCE mandatory
}|

{ ID id-MBSSessionSetupRequestTransfer
CRITICALITY reject TYPE OCTET STRING (CONTAINING MBSSessionSetupOrModRequestTransfer)
PRESENCE
mandatory
}|

{ ID id-AssociatedSessionID

CRITICALITY ignore TYPE AssociatedSessionID

PRESENCE optional
},

...
}

-- **************************************************************
--
-- BROADCAST SESSION SETUP RESPONSE
--
-- **************************************************************

BroadcastSessionSetupResponse ::= SEQUENCE {

protocolIEs
ProtocolIE-Container

{ {BroadcastSessionSetupResponseIEs} },

...
}

BroadcastSessionSetupResponseIEs NGAP-PROTOCOL-IES ::= {

{ ID id-MBS-SessionID

CRITICALITY reject TYPE MBS-SessionID

PRESENCE mandatory
}|

{ ID id-MBSSessionSetupResponseTransfer
CRITICALITY reject TYPE OCTET STRING (CONTAINING MBSSessionSetupOrModResponseTransfer) PRESENCE
optional

}|

{ ID id-CriticalityDiagnostics

CRITICALITY ignore TYPE CriticalityDiagnostics

PRESENCE optional
},

...
}

-- **************************************************************
--
-- BROADCAST SESSION SETUP FAILURE
--
-- **************************************************************

BroadcastSessionSetupFailure ::= SEQUENCE {

protocolIEs
ProtocolIE-Container

{ {BroadcastSessionSetupFailureIEs} },

...
}

BroadcastSessionSetupFailureIEs NGAP-PROTOCOL-IES ::= {

{ ID id-MBS-SessionID

CRITICALITY reject TYPE MBS-SessionID

PRESENCE mandatory
}|

{ ID id-MBSSessionSetupFailureTransfer
CRITICALITY ignore TYPE OCTET STRING (CONTAINING MBSSessionSetupOrModFailureTransfer ) PRESENCE
optional
}|

{ ID id-Cause

CRITICALITY ignore TYPE Cause

PRESENCE mandatory
}|

{ ID id-CriticalityDiagnostics

CRITICALITY ignore TYPE CriticalityDiagnostics

PRESENCE optional
},

...
}

-- **************************************************************
--
-- Broadcast Session Modification Elementary Procedure
--
-- **************************************************************

-- **************************************************************
--
-- BROADCAST SESSION MODIFICATION REQUEST
--
-- **************************************************************

BroadcastSessionModificationRequest ::= SEQUENCE {

protocolIEs
ProtocolIE-Container

{ {BroadcastSessionModificationRequestIEs} },

...
}

BroadcastSessionModificationRequestIEs NGAP-PROTOCOL-IES ::= {

{ ID id-MBS-SessionID

CRITICALITY reject TYPE MBS-SessionID

PRESENCE mandatory
}|

{ ID id-MBS-ServiceArea

CRITICALITY reject TYPE MBS-ServiceArea

PRESENCE optional
}|

{ ID id-MBSSessionModificationRequestTransfer
CRITICALITY reject TYPE OCTET STRING (CONTAINING MBSSessionSetupOrModRequestTransfer)

PRESENCE optional

},

...
}

-- **************************************************************
--
-- BROADCAST SESSION MODIFICATION RESPONSE
--
-- **************************************************************

BroadcastSessionModificationResponse ::= SEQUENCE {

protocolIEs
ProtocolIE-Container

{ {BroadcastSessionModificationResponseIEs} },

...
}

BroadcastSessionModificationResponseIEs NGAP-PROTOCOL-IES ::= {

{ ID id-MBS-SessionID

CRITICALITY reject TYPE MBS-SessionID

PRESENCE mandatory
}|

{ ID id-MBSSessionModificationResponseTransfer CRITICALITY reject TYPE OCTET STRING (CONTAINING MBSSessionSetupOrModResponseTransfer) PRESENCE
optional
}|

{ ID id-CriticalityDiagnostics

CRITICALITY ignore TYPE CriticalityDiagnostics

PRESENCE optional
},

...
}

-- **************************************************************
--
-- BROADCAST SESSION MODIFICATION  FAILURE
--
-- **************************************************************

BroadcastSessionModificationFailure ::= SEQUENCE {

protocolIEs
ProtocolIE-Container

{ {BroadcastSessionModificationFailureIEs} },

...
}

BroadcastSessionModificationFailureIEs NGAP-PROTOCOL-IES ::= {

{ ID id-MBS-SessionID

CRITICALITY reject TYPE MBS-SessionID

PRESENCE mandatory
}|

{ ID id-MBSSessionModificationFailureTransfer
CRITICALITY ignore TYPE OCTET STRING (CONTAINING MBSSessionSetupOrModFailureTransfer) PRESENCE
optional
}|

{ ID id-Cause

CRITICALITY ignore TYPE Cause

PRESENCE mandatory
}|

{ ID id-CriticalityDiagnostics

CRITICALITY ignore TYPE CriticalityDiagnostics

PRESENCE optional
},

...
}

-- **************************************************************
--
-- Broadcast Session Release Elementary Procedure
--
-- **************************************************************

-- **************************************************************
--
-- BROADCAST SESSION RELEASE REQUEST
--
-- **************************************************************

BroadcastSessionReleaseRequest ::= SEQUENCE {

protocolIEs
ProtocolIE-Container

{ {BroadcastSessionReleaseRequestIEs} },

...
}

BroadcastSessionReleaseRequestIEs NGAP-PROTOCOL-IES ::= {

{ ID id-MBS-SessionID

CRITICALITY reject TYPE MBS-SessionID

PRESENCE mandatory
}|

{ ID id-Cause

CRITICALITY ignore TYPE Cause

PRESENCE mandatory
},

...
}

-- **************************************************************
--
-- Broadcast Session Release Required Elementary Procedure
--
-- **************************************************************

-- **************************************************************
--
-- BROADCAST SESSION RELEASE REQUIRED
--
-- **************************************************************

BroadcastSessionReleaseRequired ::= SEQUENCE {

protocolIEs
ProtocolIE-Container

{ {BroadcastSessionReleaseRequiredIEs} },

...
}

BroadcastSessionReleaseRequiredIEs NGAP-PROTOCOL-IES ::= {

{ ID id-MBS-SessionID

CRITICALITY reject TYPE MBS-SessionID

PRESENCE mandatory
}|

{ ID id-Cause

CRITICALITY ignore TYPE Cause

PRESENCE mandatory
},

...
}

-- **************************************************************
--
-- BROADCAST SESSION RELEASE RESPONSE
--
-- **************************************************************

BroadcastSessionReleaseResponse ::= SEQUENCE {

protocolIEs
ProtocolIE-Container

{ {BroadcastSessionReleaseResponseIEs} },

...
}

BroadcastSessionReleaseResponseIEs NGAP-PROTOCOL-IES ::= {

{ ID id-MBS-SessionID

CRITICALITY reject TYPE MBS-SessionID

PRESENCE mandatory
}|

{ ID id-MBSSessionReleaseResponseTransfer

CRITICALITY ignore TYPE OCTET STRING (CONTAINING MBSSessionReleaseResponseTransfer)
PRESENCE
optional

}|

{ ID id-CriticalityDiagnostics

CRITICALITY ignore TYPE CriticalityDiagnostics

PRESENCE optional
},

...
}

-- **************************************************************
--
-- Broadcast Session Transport Elementary Procedure
--
-- **************************************************************

-- **************************************************************
--
-- BROADCAST SESSION TRANSPORT REQUEST
--
-- **************************************************************

BroadcastSessionTransportRequest ::= SEQUENCE {

protocolIEs
ProtocolIE-Container

{ {BroadcastSessionTransportRequestIEs} },

...
}

BroadcastSessionTransportRequestIEs NGAP-PROTOCOL-IES ::= {

{ ID id-MBS-SessionID

CRITICALITY reject TYPE MBS-SessionID

 PRESENCE mandatory
}|

{ ID id-BroadcastTransportRequestTransfer
CRITICALITY reject TYPE OCTET STRING (CONTAINING BroadcastTransportRequestTransfer)
PRESENCE
mandatory
},

...
}

-- **************************************************************
--
-- BROADCAST SESSION TRANSPORT RESPONSE

--
-- **************************************************************

BroadcastSessionTransportResponse ::= SEQUENCE {

protocolIEs
ProtocolIE-Container

{ {BroadcastSessionTransportResponseIEs} },

...
}

BroadcastSessionTransportResponseIEs NGAP-PROTOCOL-IES ::= {

{ ID id-MBS-SessionID

CRITICALITY reject TYPE MBS-SessionID

 PRESENCE mandatory
}|

{ ID id-BroadcastTransportResponseTransfer CRITICALITY reject TYPE OCTET STRING (CONTAINING BroadcastTransportResponseTransfer) PRESENCE
mandatory
}|

{ ID id-CriticalityDiagnostics

CRITICALITY ignore TYPE CriticalityDiagnostics  PRESENCE optional
},

...
}

-- **************************************************************
--
-- BROADCAST SESSION TRANSPORT FAILURE
--
-- **************************************************************

BroadcastSessionTransportFailure ::= SEQUENCE {

protocolIEs
ProtocolIE-Container

{ {BroadcastSessionTransportFailureIEs} },

...
}

BroadcastSessionTransportFailureIEs NGAP-PROTOCOL-IES ::= {

{ ID id-MBS-SessionID

CRITICALITY reject TYPE MBS-SessionID

 PRESENCE mandatory
}|

{ ID id-BroadcastTransportFailureTransfer
CRITICALITY ignore TYPE OCTET STRING (CONTAINING BroadcastTransportFailureTransfer) PRESENCE

mandatory
}|

{ ID id-Cause

CRITICALITY ignore TYPE Cause

 PRESENCE mandatory
}|

{ ID id-CriticalityDiagnostics

CRITICALITY ignore TYPE CriticalityDiagnostics  PRESENCE optional
},

...
}

-- **************************************************************
--
-- Distribution Setup Elementary Procedure
--
-- **************************************************************

-- **************************************************************
--
-- DISTRIBUTION SETUP REQUEST
--
-- **************************************************************

DistributionSetupRequest ::= SEQUENCE {

protocolIEs
ProtocolIE-Container

{ {DistributionSetupRequestIEs} },

...
}

DistributionSetupRequestIEs NGAP-PROTOCOL-IES ::= {

{ ID id-MBS-SessionID

CRITICALITY reject TYPE MBS-SessionID

PRESENCE mandatory
}|

{ ID id-MBS-AreaSessionID

CRITICALITY reject TYPE MBS-AreaSessionID

PRESENCE optional
}|

{ ID id-MBS-DistributionSetupRequestTransfer

CRITICALITY reject TYPE OCTET STRING (CONTAINING MBS-DistributionSetupRequestTransfer)

PRESENCE mandatory },

...
}

-- **************************************************************
--
-- DISTRIBUTION SETUP RESPONSE
--
-- **************************************************************

DistributionSetupResponse ::= SEQUENCE {

protocolIEs
ProtocolIE-Container

{ {DistributionSetupResponseIEs} },

...
}

DistributionSetupResponseIEs NGAP-PROTOCOL-IES ::= {

{ ID id-MBS-SessionID

CRITICALITY reject TYPE MBS-SessionID

PRESENCE mandatory
}|

{ ID id-MBS-AreaSessionID

CRITICALITY reject TYPE MBS-AreaSessionID

PRESENCE optional
}|

{ ID id-MBS-DistributionSetupResponseTransfer

CRITICALITY reject TYPE OCTET STRING (CONTAINING MBS-DistributionSetupResponseTransfer)

PRESENCE mandatory }|

{ ID id-CriticalityDiagnostics

CRITICALITY ignore TYPE CriticalityDiagnostics

PRESENCE optional
},

...
}

-- **************************************************************
--
-- DISTRIBUTION SETUP FAILURE
--
-- **************************************************************

DistributionSetupFailure ::= SEQUENCE {

protocolIEs
ProtocolIE-Container

{ {DistributionSetupFailureIEs} },

...
}

DistributionSetupFailureIEs NGAP-PROTOCOL-IES ::= {

{ ID id-MBS-SessionID

CRITICALITY reject TYPE MBS-SessionID

PRESENCE mandatory
}|

{ ID id-MBS-AreaSessionID

CRITICALITY reject TYPE MBS-AreaSessionID

PRESENCE optional
}|

{ ID id-MBS-DistributionSetupUnsuccessfulTransfer
CRITICALITY ignore TYPE OCTET STRING (CONTAINING MBS-DistributionSetupUnsuccessfulTransfer) PRESENCE mandatory }|

{ ID id-Cause

CRITICALITY ignore TYPE Cause

PRESENCE mandatory
}|

{ ID id-CriticalityDiagnostics

CRITICALITY ignore TYPE CriticalityDiagnostics

PRESENCE optional
},

...
}

-- **************************************************************
--
-- Distribution Release Elementary Procedure
--

-- **************************************************************

-- **************************************************************
--
-- DISTRIBUTION RELEASE REQUEST
--
-- **************************************************************

DistributionReleaseRequest ::= SEQUENCE {

protocolIEs
ProtocolIE-Container

{ {DistributionReleaseRequestIEs} },

...
}

DistributionReleaseRequestIEs NGAP-PROTOCOL-IES ::= {

{ ID id-MBS-SessionID

CRITICALITY reject TYPE MBS-SessionID

PRESENCE mandatory
}|

{ ID id-MBS-AreaSessionID

CRITICALITY reject TYPE MBS-AreaSessionID

PRESENCE optional
}|

{ ID id-MBS-DistributionReleaseRequestTransfer
CRITICALITY reject TYPE OCTET STRING (CONTAINING MBS-DistributionReleaseRequestTransfer)

PRESENCE mandatory }|

{ ID id-Cause

CRITICALITY ignore TYPE Cause

PRESENCE mandatory
},

...
}

-- **************************************************************
--
-- DISTRIBUTION RELEASE RESPONSE
--
-- **************************************************************

DistributionReleaseResponse ::= SEQUENCE {

protocolIEs
ProtocolIE-Container

{ {DistributionReleaseResponseIEs} },

...
}

DistributionReleaseResponseIEs NGAP-PROTOCOL-IES ::= {

{ ID id-MBS-SessionID

CRITICALITY reject TYPE MBS-SessionID

PRESENCE mandatory
}|

{ ID id-MBS-AreaSessionID

CRITICALITY reject TYPE MBS-AreaSessionID

PRESENCE optional
}|

{ ID id-CriticalityDiagnostics

CRITICALITY ignore TYPE CriticalityDiagnostics

PRESENCE optional
},

...
}

-- **************************************************************
--
-- Multicast Session Activation Elementary Procedure
--
-- **************************************************************

-- **************************************************************
--
-- MULTICAST SESSION ACTIVATION REQUEST
--
-- **************************************************************

MulticastSessionActivationRequest ::= SEQUENCE {

protocolIEs
ProtocolIE-Container

{ {MulticastSessionActivationRequestIEs} },

...
}

MulticastSessionActivationRequestIEs NGAP-PROTOCOL-IES ::= {

{ ID id-MBS-SessionID

CRITICALITY reject TYPE MBS-SessionID

PRESENCE mandatory
}|

{ ID id-MulticastSessionActivationRequestTransfer
CRITICALITY reject TYPE OCTET STRING (CONTAINING
MulticastSessionActivationRequestTransfer) PRESENCE mandatory },

...
}

-- **************************************************************
--
-- MULTICAST SESSION ACTIVATION RESPONSE
--
-- **************************************************************

MulticastSessionActivationResponse ::= SEQUENCE {

protocolIEs
ProtocolIE-Container

{ {MulticastSessionActivationResponseIEs} },

...
}

MulticastSessionActivationResponseIEs NGAP-PROTOCOL-IES ::= {

{ ID id-MBS-SessionID

CRITICALITY reject TYPE MBS-SessionID

PRESENCE mandatory
}|

{ ID id-CriticalityDiagnostics

CRITICALITY ignore TYPE CriticalityDiagnostics

PRESENCE optional
},

...
}

-- **************************************************************
--
-- MULTICAST SESSION ACTIVATION FAILURE
--
-- **************************************************************

MulticastSessionActivationFailure ::= SEQUENCE {

protocolIEs
ProtocolIE-Container

{ {MulticastSessionActivationFailureIEs} },

...
}

MulticastSessionActivationFailureIEs NGAP-PROTOCOL-IES ::= {

{ ID id-MBS-SessionID

CRITICALITY reject TYPE MBS-SessionID

PRESENCE mandatory

}|

{ ID id-Cause

CRITICALITY ignore TYPE Cause

PRESENCE mandatory

}|

{ ID id-CriticalityDiagnostics

CRITICALITY ignore TYPE CriticalityDiagnostics

PRESENCE optional

},

...
}

-- **************************************************************
--
-- Multicast Session Deactivation Elementary Procedure
--
-- **************************************************************

-- **************************************************************
--
-- MULTICAST SESSION DEACTIVATION REQUEST
--
-- **************************************************************

MulticastSessionDeactivationRequest ::= SEQUENCE {

protocolIEs
ProtocolIE-Container

{ {MulticastSessionDeactivationRequestIEs} },

...
}

MulticastSessionDeactivationRequestIEs NGAP-PROTOCOL-IES ::= {

{ ID id-MBS-SessionID

CRITICALITY reject TYPE MBS-SessionID

PRESENCE mandatory
}|

{ ID id-MulticastSessionDeactivationRequestTransfer CRITICALITY reject TYPE OCTET STRING (CONTAINING
MulticastSessionDeactivationRequestTransfer)
PRESENCE mandatory },

...
}

-- **************************************************************
--
-- MULTICAST SESSION DEACTIVATION RESPONSE
--
-- **************************************************************

MulticastSessionDeactivationResponse ::= SEQUENCE {

protocolIEs
ProtocolIE-Container

{ {MulticastSessionDeactivationResponseIEs} },

...
}

MulticastSessionDeactivationResponseIEs NGAP-PROTOCOL-IES ::= {

{ ID id-MBS-SessionID

CRITICALITY reject TYPE MBS-SessionID

PRESENCE mandatory

}|

{ ID id-CriticalityDiagnostics

CRITICALITY ignore TYPE CriticalityDiagnostics

PRESENCE optional

},

...
}

-- **************************************************************
--
-- Multicast Session Update Elementary Procedure
--
-- **************************************************************

-- **************************************************************
--
-- MULTICAST SESSION UPDATE REQUEST
--
-- **************************************************************

MulticastSessionUpdateRequest ::= SEQUENCE {

protocolIEs
ProtocolIE-Container

{ {MulticastSessionUpdateRequestIEs} },

...
}

MulticastSessionUpdateRequestIEs NGAP-PROTOCOL-IES ::= {

{ ID id-MBS-SessionID

CRITICALITY reject TYPE MBS-SessionID

PRESENCE mandatory
}|

{ ID id-MBS-AreaSessionID

CRITICALITY reject TYPE MBS-AreaSessionID

PRESENCE optional
}|

{ ID id-MulticastSessionUpdateRequestTransfer

CRITICALITY reject TYPE OCTET STRING (CONTAINING MulticastSessionUpdateRequestTransfer)

PRESENCE mandatory },

...
}

-- **************************************************************
--
-- MULTICAST SESSION UPDATE RESPONSE
--
-- **************************************************************

MulticastSessionUpdateResponse ::= SEQUENCE {

protocolIEs
ProtocolIE-Container

{ {MulticastSessionUpdateResponseIEs} },

...
}

MulticastSessionUpdateResponseIEs NGAP-PROTOCOL-IES ::= {

{ ID id-MBS-SessionID

CRITICALITY reject TYPE MBS-SessionID

PRESENCE mandatory
}|

{ ID id-MBS-AreaSessionID

CRITICALITY reject TYPE MBS-AreaSessionID

PRESENCE optional
}|

{ ID id-CriticalityDiagnostics

CRITICALITY ignore TYPE CriticalityDiagnostics

PRESENCE optional
},

...
}

-- **************************************************************
--
-- MULTICAST SESSION UPDATE FAILURE
--
-- **************************************************************

MulticastSessionUpdateFailure ::= SEQUENCE {

protocolIEs
ProtocolIE-Container

{ {MulticastSessionUpdateFailureIEs} },

...
}

MulticastSessionUpdateFailureIEs NGAP-PROTOCOL-IES ::= {

{ ID id-MBS-SessionID

CRITICALITY reject TYPE MBS-SessionID

PRESENCE mandatory

}|

{ ID id-MBS-AreaSessionID

CRITICALITY reject TYPE MBS-AreaSessionID

PRESENCE optional

}|

{ ID id-Cause

CRITICALITY ignore TYPE Cause

PRESENCE mandatory

}|

{ ID id-CriticalityDiagnostics

CRITICALITY ignore TYPE CriticalityDiagnostics

PRESENCE optional

},

...
}

-- **************************************************************
--
-- MULTICAST GROUP PAGING ELEMENTARY PROCEDURE
--
-- **************************************************************

-- **************************************************************
--
-- MULTICAST GROUP PAGING
--
-- **************************************************************

MulticastGroupPaging ::= SEQUENCE {

protocolIEs
ProtocolIE-Container

{ {MulticastGroupPagingIEs} },

...
}

MulticastGroupPagingIEs NGAP-PROTOCOL-IES ::= {

{ ID id-MBS-SessionID

CRITICALITY ignore TYPE MBS-SessionID

PRESENCE mandatory
}|

{ ID id-MBS-ServiceArea

CRITICALITY ignore TYPE MBS-ServiceArea

PRESENCE optional
}|

{ ID id-MulticastGroupPagingAreaList

CRITICALITY ignore TYPE MulticastGroupPagingAreaList PRESENCE mandatory
},

...
}

-- **************************************************************
--
-- TIMING SYNCHRONISATION STATUS REPORTING ELEMENTARY PROCEDURES
--
-- **************************************************************

-- **************************************************************
--
-- Timing Synchronisation Status Elementary Procedure
--
-- **************************************************************

-- **************************************************************
--
-- TIMING SYNCHRONISATION STATUS REQUEST
--
-- **************************************************************

TimingSynchronisationStatusRequest ::= SEQUENCE {

protocolIEs
ProtocolIE-Container

{ {TimingSynchronisationStatusRequestIEs} },

...
}

TimingSynchronisationStatusRequestIEs NGAP-PROTOCOL-IES ::= {

{ ID id-RoutingID

CRITICALITY reject TYPE RoutingID

PRESENCE mandatory
}|

{ ID id-RAN-TSSRequestType
CRITICALITY reject TYPE RAN-TSSRequestType PRESENCE mandatory
},

...
}

-- **************************************************************
--
-- TIMING SYNCHRONISATION STATUS RESPONSE
--
-- **************************************************************

TimingSynchronisationStatusResponse ::= SEQUENCE {

protocolIEs
ProtocolIE-Container

{ {TimingSynchronisationStatusResponseIEs} },

...
}

TimingSynchronisationStatusResponseIEs NGAP-PROTOCOL-IES ::= {

{ ID id-RoutingID

CRITICALITY ignore TYPE RoutingID

PRESENCE mandatory
}|

{ ID id-CriticalityDiagnostics
CRITICALITY ignore TYPE CriticalityDiagnostics
PRESENCE optional
},

...
}

-- **************************************************************
--
-- TIMING SYNCHRONISATION STATUS FAILURE
--
-- **************************************************************

TimingSynchronisationStatusFailure ::= SEQUENCE {

protocolIEs
ProtocolIE-Container

{ { TimingSynchronisationStatusFailureIEs} },

...
}

TimingSynchronisationStatusFailureIEs NGAP-PROTOCOL-IES ::= {

{ ID id-RoutingID

CRITICALITY ignore TYPE RoutingID

 PRESENCE mandatory
}|

{ ID id-Cause

CRITICALITY ignore TYPE Cause

 PRESENCE mandatory
}|

{ ID id-CriticalityDiagnostics

CRITICALITY ignore TYPE CriticalityDiagnostics  PRESENCE optional
},

...
}

-- **************************************************************
--
-- Timing Synchronisation Status Reporting Elementary Procedure
--
-- **************************************************************

-- **************************************************************
--
-- TIMING SYNCHRONISATION STATUS REPORT
--
-- **************************************************************

TimingSynchronisationStatusReport ::= SEQUENCE {

protocolIEs

ProtocolIE-Container

{ {TimingSynchronisationStatusReportIEs} },

...
}

TimingSynchronisationStatusReportIEs NGAP-PROTOCOL-IES ::= {

{ ID id-RoutingID

CRITICALITY ignore TYPE RoutingID

PRESENCE mandatory
}|

{ ID id-RANTimingSynchronisationStatusInfo
CRITICALITY ignore TYPE RANTimingSynchronisationStatusInfo

PRESENCE mandatory
}|

{ ID id-RAN-TSSScope

CRITICALITY ignore TYPE RAN-TSSScope

PRESENCE mandatory
},

...
}

-- **************************************************************
--
-- MT Communication Handling Elementary Procedure
--
-- **************************************************************

-- **************************************************************
--
-- MT COMMUNICATION HANDLING REQUEST
--
-- **************************************************************

MTCommunicationHandlingRequest ::= SEQUENCE {

protocolIEs
ProtocolIE-Container

{ { MTCommunicationHandlingRequestIEs} },

...
}

MTCommunicationHandlingRequestIEs NGAP-PROTOCOL-IES ::= {

{ ID id-AMF-UE-NGAP-ID

CRITICALITY reject TYPE AMF-UE-NGAP-ID

 PRESENCE mandatory
}|

{ ID id-RAN-UE-NGAP-ID

CRITICALITY reject TYPE RAN-UE-NGAP-ID

 PRESENCE mandatory
}|

{ ID id-FiveGCAction

CRITICALITY reject TYPE FiveGCAction

 PRESENCE mandatory
}|

{ ID id-PDUSessionListMTCommHReq

CRITICALITY reject TYPE PDUSessionListMTCommHReq
 PRESENCE mandatory
},

...
}

-- **************************************************************
--
-- MT COMMUNICATION HANDLING RESPONSE
--
-- **************************************************************

MTCommunicationHandlingResponse ::= SEQUENCE {

protocolIEs
ProtocolIE-Container

{ {MTCommunicationHandlingResponseIEs} },

...
}

MTCommunicationHandlingResponseIEs NGAP-PROTOCOL-IES ::= {

{ ID id-AMF-UE-NGAP-ID

CRITICALITY reject TYPE AMF-UE-NGAP-ID

PRESENCE mandatory
}|

{ ID id-RAN-UE-NGAP-ID

CRITICALITY reject TYPE RAN-UE-NGAP-ID

PRESENCE mandatory
}|

{ ID id-CriticalityDiagnostics

CRITICALITY ignore TYPE CriticalityDiagnostics

PRESENCE optional
},

...
}

-- **************************************************************
--
-- MT COMMUNICATION HANDLING FAILURE
--
-- **************************************************************

MTCommunicationHandlingFailure ::= SEQUENCE {

protocolIEs
ProtocolIE-Container

{ { MTCommunicationHandlingFailureIEs} },

...
}

MTCommunicationHandlingFailureIEs NGAP-PROTOCOL-IES ::= {

{ ID id-AMF-UE-NGAP-ID

CRITICALITY reject TYPE AMF-UE-NGAP-ID

PRESENCE mandatory
}|

{ ID id-RAN-UE-NGAP-ID

CRITICALITY reject TYPE RAN-UE-NGAP-ID

PRESENCE mandatory
}|

{ ID id-Cause

CRITICALITY ignore TYPE Cause

PRESENCE mandatory
}|

{ ID id-CriticalityDiagnostics
CRITICALITY ignore TYPE CriticalityDiagnostics
PRESENCE optional
},

...
}

-- **************************************************************

-- RAN Paging Request procedure
--
-- **************************************************************

-- **************************************************************
--
-- RAN PAGING REQUEST
--
-- **************************************************************

RANPagingRequest ::= SEQUENCE {

protocolIEs

ProtocolIE-Container       { {  RANPagingRequestIEs} },

...
}

RANPagingRequestIEs NGAP-PROTOCOL-IES ::= {

{ ID id-AMF-UE-NGAP-ID

CRITICALITY ignore TYPE AMF-UE-NGAP-ID

PRESENCE mandatory
}|

{ ID id-RAN-UE-NGAP-ID

CRITICALITY ignore TYPE RAN-UE-NGAP-ID

PRESENCE mandatory
}|

{ ID id-PagingPolicyDifferentiation
CRITICALITY ignore TYPE PagingPolicyDifferentiation
PRESENCE optional
}|

{ ID id-DL-Signalling

CRITICALITY ignore TYPE DL-Signalling

PRESENCE optional
},

...
}

-- **************************************************************
--
-- A-IoT ELEMENTARY PROCEDURES
--
-- **************************************************************

-- **************************************************************
--
-- Inventory Request Elementary Procedure
--
-- **************************************************************

-- **************************************************************
--
-- INVENTORY REQUEST
--
-- **************************************************************

InventoryRequest ::= SEQUENCE {

protocolIEs
ProtocolIE-Container

{ {InventoryRequestIEs} },

...
}

InventoryRequestIEs NGAP-PROTOCOL-IES ::= {

{ ID id-AIOTFIdentifier

CRITICALITY reject TYPE AIOTFIdentifier

PRESENCE mandatory
}|

{ ID id-AIoT-CorrelationIdentifier CRITICALITY reject TYPE AIoT-CorrelationIdentifier

PRESENCE mandatory
}|

{ ID id-InventoryRequestTransfer
CRITICALITY reject TYPE OCTET STRING (CONTAINING InventoryRequestTransfer)
PRESENCE mandatory
},

...
}

-- **************************************************************
--
-- INVENTORY RESPONSE
--
-- **************************************************************

InventoryResponse ::= SEQUENCE {

protocolIEs
ProtocolIE-Container

{ {InventoryResponseIEs} },

...
}

InventoryResponseIEs NGAP-PROTOCOL-IES ::= {

{ ID id-AIOTFIdentifier

CRITICALITY reject TYPE AIOTFIdentifier

PRESENCE mandatory
}|

{ ID id-AIoT-CorrelationIdentifier CRITICALITY reject TYPE AIoT-CorrelationIdentifier

PRESENCE mandatory
}|

{ ID id-InventoryResponseTransfer
CRITICALITY reject TYPE OCTET STRING (CONTAINING InventoryResponseTransfer) PRESENCE mandatory
}|

{ ID id-CriticalityDiagnostics
CRITICALITY ignore TYPE CriticalityDiagnostics

PRESENCE optional
},

...
}

-- **************************************************************
--
-- INVENTORY FAILURE
--
-- **************************************************************

InventoryFailure ::= SEQUENCE {

protocolIEs
ProtocolIE-Container

{ {InventoryFailureIEs} },

...
}

InventoryFailureIEs NGAP-PROTOCOL-IES ::= {

{ ID id-AIOTFIdentifier

CRITICALITY ignore TYPE AIOTFIdentifier

PRESENCE mandatory
}|

{ ID id-AIoT-CorrelationIdentifier CRITICALITY ignore TYPE AIoT-CorrelationIdentifier

PRESENCE mandatory
}|

{ ID id-InventoryFailureTransfer
CRITICALITY ignore TYPE OCTET STRING (CONTAINING InventoryFailureTransfer ) PRESENCE mandatory
}|

{ ID id-Cause

CRITICALITY ignore TYPE Cause

PRESENCE mandatory
}|

{ ID id-CriticalityDiagnostics
CRITICALITY ignore TYPE CriticalityDiagnostics

PRESENCE optional
},

...
}

-- **************************************************************

-- Inventory Report procedure
--
-- **************************************************************

-- **************************************************************
--
-- INVENTORY REPORT
--
-- **************************************************************

InventoryReport ::= SEQUENCE {

protocolIEs

ProtocolIE-Container       { {  InventoryReportIEs} },

...
}

InventoryReportIEs NGAP-PROTOCOL-IES ::= {

{ ID id-AIOTFIdentifier

CRITICALITY reject TYPE AIOTFIdentifier

PRESENCE mandatory
}|

{ ID id-AIoT-CorrelationIdentifier CRITICALITY reject TYPE AIoT-CorrelationIdentifier

PRESENCE mandatory
}|

{ ID id-InventoryReportTransfer
CRITICALITY reject TYPE OCTET STRING (CONTAINING InventoryReportTransfer
) PRESENCE mandatory
},

...
}

-- **************************************************************
--
-- Command Request Elementary Procedure
--
-- **************************************************************

-- **************************************************************
--
-- COMMAND REQUEST
--
-- **************************************************************

CommandRequest ::= SEQUENCE {

protocolIEs
ProtocolIE-Container

{ {CommandRequestIEs} },

...
}

CommandRequestIEs NGAP-PROTOCOL-IES ::= {

{ ID id-AIOTFIdentifier

CRITICALITY reject TYPE AIOTFIdentifier

PRESENCE mandatory
}|

{ ID id-AIoT-CorrelationIdentifier CRITICALITY reject TYPE AIoT-CorrelationIdentifier

PRESENCE mandatory
}|

{ ID id-RAN-AIOT-Device-NGAP-ID
CRITICALITY reject TYPE RAN-AIOT-Device-NGAP-ID

PRESENCE mandatory
}|

{ ID id-CommandRequestTransfer
CRITICALITY reject TYPE OCTET STRING (CONTAINING CommandRequestTransfer)

PRESENCE mandatory
},

...
}

-- **************************************************************
--
-- COMMAND RESPONSE
--
-- **************************************************************

CommandResponse ::= SEQUENCE {

protocolIEs
ProtocolIE-Container

{ {CommandResponseIEs} },

...
}

CommandResponseIEs NGAP-PROTOCOL-IES ::= {

{ ID id-AIOTFIdentifier

CRITICALITY reject TYPE AIOTFIdentifier

PRESENCE mandatory
}|

{ ID id-AIoT-CorrelationIdentifier CRITICALITY reject TYPE AIoT-CorrelationIdentifier

PRESENCE mandatory
}|

{ ID id-RAN-AIOT-Device-NGAP-ID
CRITICALITY reject TYPE RAN-AIOT-Device-NGAP-ID

PRESENCE mandatory
}|

{ ID id-CommandResponseTransfer
CRITICALITY reject TYPE OCTET STRING (CONTAINING CommandResponseTransfer)
PRESENCE mandatory
}|

{ ID id-CriticalityDiagnostics
CRITICALITY ignore TYPE CriticalityDiagnostics

PRESENCE optional
},

...
}

-- **************************************************************
--
-- COMMAND FAILURE
--
-- **************************************************************

CommandFailure ::= SEQUENCE {

protocolIEs
ProtocolIE-Container

{ {CommandFailureIEs} },

...
}

CommandFailureIEs NGAP-PROTOCOL-IES ::= {

{ ID id-AIOTFIdentifier

CRITICALITY ignore TYPE AIOTFIdentifier

PRESENCE mandatory
}|

{ ID id-AIoT-CorrelationIdentifier CRITICALITY ignore TYPE AIoT-CorrelationIdentifier

PRESENCE mandatory
}|

{ ID id-RAN-AIOT-Device-NGAP-ID
CRITICALITY ignore TYPE RAN-AIOT-Device-NGAP-ID

PRESENCE mandatory
}|

{ ID id-CommandFailureTransfer
CRITICALITY ignore TYPE OCTET STRING (CONTAINING CommandFailureTransfer )
PRESENCE mandatory
}|

{ ID id-Cause

CRITICALITY ignore TYPE Cause

PRESENCE mandatory
}|

{ ID id-CriticalityDiagnostics
CRITICALITY ignore TYPE CriticalityDiagnostics

PRESENCE optional
},

...
}

-- **************************************************************
--
-- A-IoT Session Release Elementary Procedure
--
-- **************************************************************

-- **************************************************************
--
-- AIOT SESSION RELEASE COMMAND
--
-- **************************************************************

AIOTSessionReleaseCommand ::= SEQUENCE {

protocolIEs
ProtocolIE-Container

{ {AIOTSessionReleaseCommandIEs} },

...
}

AIOTSessionReleaseCommandIEs NGAP-PROTOCOL-IES ::= {

{ ID id-AIOTFIdentifier

CRITICALITY reject TYPE AIOTFIdentifier

PRESENCE mandatory
}|

{ ID id-AIoT-CorrelationIdentifier

CRITICALITY reject TYPE AIoT-CorrelationIdentifier

PRESENCE mandatory
}|

{ ID id-AIOTSessionReleaseCommandTransfer
CRITICALITY reject TYPE OCTET STRING (CONTAINING AIOTSessionReleaseCommandTransfer)
PRESENCE
mandatory
},

...

}

-- **************************************************************
--
-- AIOT SESSION RELEASE COMPLETE
--
-- **************************************************************

AIOTSessionReleaseComplete ::= SEQUENCE {

protocolIEs
ProtocolIE-Container

{ {AIOTSessionReleaseCompleteIEs} },

...
}

AIOTSessionReleaseCompleteIEs NGAP-PROTOCOL-IES ::= {

{ ID id-AIOTFIdentifier

CRITICALITY ignore TYPE AIOTFIdentifier

PRESENCE mandatory
}|

{ ID id-AIoT-CorrelationIdentifier

CRITICALITY ignore TYPE AIoT-CorrelationIdentifier

PRESENCE mandatory
}|

{ ID id-AIOTSessionReleaseCompleteTransfer CRITICALITY ignore TYPE OCTET STRING (CONTAINING AIOTSessionReleaseCompleteTransfer) PRESENCE
mandatory
}|

{ ID id-CriticalityDiagnostics

CRITICALITY ignore TYPE CriticalityDiagnostics

PRESENCE optional
},

...
}

-- **************************************************************
--
-- A-IoT Session Release Request Elementary Procedure
--
-- **************************************************************

-- **************************************************************
--
-- AIOT SESSION RELEASE REQUEST
--
-- **************************************************************

AIOTSessionReleaseRequest ::= SEQUENCE {

protocolIEs
ProtocolIE-Container

{ {AIOTSessionReleaseRequestIEs} },

...
}

AIOTSessionReleaseRequestIEs NGAP-PROTOCOL-IES ::= {

{ ID id-AIOTFIdentifier

CRITICALITY reject TYPE AIOTFIdentifier

PRESENCE mandatory
}|

{ ID id-AIoT-CorrelationIdentifier

CRITICALITY reject TYPE AIoT-CorrelationIdentifier

PRESENCE mandatory
}|

{ ID id-AIOTSessionReleaseRequestTransfer
CRITICALITY reject TYPE OCTET STRING (CONTAINING AIOTSessionReleaseRequestTransfer)
PRESENCE
mandatory
},

...
}

END
-- ASN1STOP
