-- ASN1START

-- **************************************************************
--
-- Elementary Procedure definitions
--
-- **************************************************************

NGAP-PDU-Descriptions  {
itu-t (0) identified-organization (4) etsi (0) mobileDomain (0)
ngran-Access (22) modules (3) ngap (1) version1 (1) ngap-PDU-Descriptions (0)}

DEFINITIONS AUTOMATIC TAGS ::=

BEGIN

-- **************************************************************
--
-- IE parameter types from other modules.
--
-- **************************************************************

IMPORTS

Criticality,

ProcedureCode
FROM NGAP-CommonDataTypes

AMFConfigurationUpdate,

AMFConfigurationUpdateAcknowledge,

AMFConfigurationUpdateFailure,

AMFCPRelocationIndication,

AMFStatusIndication,

BroadcastSessionModificationFailure,

BroadcastSessionModificationRequest,

BroadcastSessionModificationResponse,

BroadcastSessionReleaseRequest,

BroadcastSessionReleaseRequired,

BroadcastSessionReleaseResponse,

BroadcastSessionSetupFailure,

BroadcastSessionSetupRequest,

BroadcastSessionSetupResponse,

BroadcastSessionTransportFailure,

BroadcastSessionTransportRequest,

BroadcastSessionTransportResponse,

CellTrafficTrace,

ConnectionEstablishmentIndication,

DeactivateTrace,

DistributionReleaseRequest,

DistributionReleaseResponse,

DistributionSetupFailure,

DistributionSetupRequest,

DistributionSetupResponse,

DownlinkNASTransport,

DownlinkNonUEAssociatedNRPPaTransport,

DownlinkRANConfigurationTransfer,

DownlinkRANEarlyStatusTransfer,

DownlinkRANStatusTransfer,

DownlinkUEAssociatedNRPPaTransport,

ErrorIndication,

HandoverCancel,

HandoverCancelAcknowledge,

HandoverCommand,

HandoverFailure,

HandoverNotify,

HandoverPreparationFailure,

HandoverRequest,

HandoverRequestAcknowledge,

HandoverRequired,

HandoverSuccess,

InitialContextSetupFailure,

InitialContextSetupRequest,

InitialContextSetupResponse,

InitialUEMessage,

LocationReport,

LocationReportingControl,

LocationReportingFailureIndication,

MTCommunicationHandlingRequest,

MTCommunicationHandlingResponse,

MTCommunicationHandlingFailure,

MulticastSessionActivationFailure,

MulticastSessionActivationRequest,

MulticastSessionActivationResponse,

MulticastSessionDeactivationRequest,

MulticastSessionDeactivationResponse,

MulticastSessionUpdateFailure,

MulticastSessionUpdateRequest,

MulticastSessionUpdateResponse,

MulticastGroupPaging,

NASNonDeliveryIndication,

NGReset,

NGResetAcknowledge,

NGRemovalFailure,

NGRemovalRequest,

NGRemovalResponse,

NGSetupFailure,

NGSetupRequest,

NGSetupResponse,

OverloadStart,

OverloadStop,

Paging,

PathSwitchRequest,

PathSwitchRequestAcknowledge,

PathSwitchRequestFailure,

PDUSessionResourceModifyConfirm,

PDUSessionResourceModifyIndication,

PDUSessionResourceModifyRequest,

PDUSessionResourceModifyResponse,

PDUSessionResourceNotify,

PDUSessionResourceReleaseCommand,

PDUSessionResourceReleaseResponse,

PDUSessionResourceSetupRequest,

PDUSessionResourceSetupResponse,

PrivateMessage,

PWSCancelRequest,

PWSCancelResponse,

PWSFailureIndication,

PWSRestartIndication,

RANConfigurationUpdate,

RANConfigurationUpdateAcknowledge,

RANConfigurationUpdateFailure,

RANCPRelocationIndication,

RANPagingRequest,

RerouteNASRequest,

RetrieveUEInformation,

RRCInactiveTransitionReport,

SecondaryRATDataUsageReport,

TimingSynchronisationStatusRequest,

TimingSynchronisationStatusResponse,

TimingSynchronisationStatusFailure,

TimingSynchronisationStatusReport,

TraceFailureIndication,

TraceStart,

UEContextModificationFailure,

UEContextModificationRequest,

UEContextModificationResponse,

UEContextReleaseCommand,

UEContextReleaseComplete,

UEContextReleaseRequest,

UEContextResumeRequest,

UEContextResumeResponse,

UEContextResumeFailure,

UEContextSuspendRequest,

UEContextSuspendResponse,

UEContextSuspendFailure,

UEInformationTransfer,

UERadioCapabilityCheckRequest,

UERadioCapabilityCheckResponse,

UERadioCapabilityIDMappingRequest,

UERadioCapabilityIDMappingResponse,

UERadioCapabilityInfoIndication,

UETNLABindingReleaseRequest,

UplinkNASTransport,

UplinkNonUEAssociatedNRPPaTransport,

UplinkRANConfigurationTransfer,

UplinkRANEarlyStatusTransfer,

UplinkRANStatusTransfer,

UplinkUEAssociatedNRPPaTransport,

WriteReplaceWarningRequest,

WriteReplaceWarningResponse,

UplinkRIMInformationTransfer,

DownlinkRIMInformationTransfer,

InventoryRequest,

InventoryResponse,

InventoryFailure,

InventoryReport,

CommandRequest,

CommandResponse,

CommandFailure,

AIOTSessionReleaseCommand,

AIOTSessionReleaseComplete,

AIOTSessionReleaseRequest

FROM NGAP-PDU-Contents

id-AMFConfigurationUpdate,

id-AMFCPRelocationIndication,

id-AMFStatusIndication,

id-BroadcastSessionModification,

id-BroadcastSessionRelease,

id-BroadcastSessionReleaseRequired,

id-BroadcastSessionSetup,

id-BroadcastSessionTransport,

id-CellTrafficTrace,

id-ConnectionEstablishmentIndication,

id-DeactivateTrace,

id-DistributionRelease,

id-DistributionSetup,

id-DownlinkNASTransport,

id-DownlinkNonUEAssociatedNRPPaTransport,

id-DownlinkRANConfigurationTransfer,

id-DownlinkRANEarlyStatusTransfer,

id-DownlinkRANStatusTransfer,

id-DownlinkRIMInformationTransfer,

id-DownlinkUEAssociatedNRPPaTransport,

id-ErrorIndication,

id-HandoverCancel,

id-HandoverNotification,

id-HandoverPreparation,

id-HandoverResourceAllocation,

id-HandoverSuccess,

id-InitialContextSetup,

id-InitialUEMessage,

id-LocationReport,

id-LocationReportingControl,

id-LocationReportingFailureIndication,

id-MTCommunicationHandling,

id-MulticastGroupPaging,

id-MulticastSessionActivation,

id-MulticastSessionDeactivation,

id-MulticastSessionUpdate,

id-NASNonDeliveryIndication,

id-NGReset,

id-NGRemoval,

id-NGSetup,

id-OverloadStart,

id-OverloadStop,

id-Paging,

id-PathSwitchRequest,

id-PDUSessionResourceModify,

id-PDUSessionResourceModifyIndication,

id-PDUSessionResourceNotify,

id-PDUSessionResourceRelease,

id-PDUSessionResourceSetup,

id-PrivateMessage,

id-PWSCancel,

id-PWSFailureIndication,

id-PWSRestartIndication,

id-RANConfigurationUpdate,

id-RANCPRelocationIndication,

id-RANPagingRequest,

id-RerouteNASRequest,

id-RetrieveUEInformation,

id-RRCInactiveTransitionReport,

id-SecondaryRATDataUsageReport,

id-TimingSynchronisationStatus,

id-TimingSynchronisationStatusReport,

id-TraceFailureIndication,

id-TraceStart,

id-UEContextModification,

id-UEContextRelease,

id-UEContextReleaseRequest,

id-UEContextResume,

id-UEContextSuspend,

id-UEInformationTransfer,

id-UERadioCapabilityCheck,

id-UERadioCapabilityIDMapping,

id-UERadioCapabilityInfoIndication,

id-UETNLABindingRelease,

id-UplinkNASTransport,

id-UplinkNonUEAssociatedNRPPaTransport,

id-UplinkRANConfigurationTransfer,

id-UplinkRANEarlyStatusTransfer,

id-UplinkRANStatusTransfer,

id-UplinkRIMInformationTransfer,

id-UplinkUEAssociatedNRPPaTransport,

id-WriteReplaceWarning,

id-InventoryRequest,

id-InventoryReport,

id-CommandRequest,

id-AIOTSessionRelease,

id-AIOTSessionReleaseRequest

FROM NGAP-Constants;

-- **************************************************************

--
-- Interface Elementary Procedure Class
--
-- **************************************************************

NGAP-ELEMENTARY-PROCEDURE ::= CLASS {

&InitiatingMessage

,

&SuccessfulOutcome

OPTIONAL,

&UnsuccessfulOutcome

OPTIONAL,

&procedureCode

ProcedureCode
UNIQUE,

&criticality

Criticality DEFAULT ignore
}

WITH SYNTAX {

INITIATING MESSAGE

&InitiatingMessage

[SUCCESSFUL OUTCOME

&SuccessfulOutcome]

[UNSUCCESSFUL OUTCOME

&UnsuccessfulOutcome]

PROCEDURE CODE

&procedureCode

[CRITICALITY

&criticality]
}

-- **************************************************************
--
-- Interface PDU Definition
--
-- **************************************************************

NGAP-PDU ::= CHOICE {

initiatingMessage

InitiatingMessage,

successfulOutcome

SuccessfulOutcome,

unsuccessfulOutcome

UnsuccessfulOutcome,

...
}

InitiatingMessage ::= SEQUENCE {

procedureCode
NGAP-ELEMENTARY-PROCEDURE.&procedureCode

({NGAP-ELEMENTARY-PROCEDURES}),

criticality
NGAP-ELEMENTARY-PROCEDURE.&criticality

({NGAP-ELEMENTARY-PROCEDURES}{@procedureCode}),

value

NGAP-ELEMENTARY-PROCEDURE.&InitiatingMessage
({NGAP-ELEMENTARY-PROCEDURES}{@procedureCode})
}

SuccessfulOutcome ::= SEQUENCE {

procedureCode
NGAP-ELEMENTARY-PROCEDURE.&procedureCode

({NGAP-ELEMENTARY-PROCEDURES}),

criticality
NGAP-ELEMENTARY-PROCEDURE.&criticality

({NGAP-ELEMENTARY-PROCEDURES}{@procedureCode}),

value

NGAP-ELEMENTARY-PROCEDURE.&SuccessfulOutcome
({NGAP-ELEMENTARY-PROCEDURES}{@procedureCode})
}

UnsuccessfulOutcome ::= SEQUENCE {

procedureCode
NGAP-ELEMENTARY-PROCEDURE.&procedureCode

({NGAP-ELEMENTARY-PROCEDURES}),

criticality
NGAP-ELEMENTARY-PROCEDURE.&criticality

({NGAP-ELEMENTARY-PROCEDURES}{@procedureCode}),

value

NGAP-ELEMENTARY-PROCEDURE.&UnsuccessfulOutcome ({NGAP-ELEMENTARY-PROCEDURES}{@procedureCode})
}

-- **************************************************************
--

-- Interface Elementary Procedure List
--
-- **************************************************************

NGAP-ELEMENTARY-PROCEDURES NGAP-ELEMENTARY-PROCEDURE ::= {

NGAP-ELEMENTARY-PROCEDURES-CLASS-1

|

NGAP-ELEMENTARY-PROCEDURES-CLASS-2,

...
}

NGAP-ELEMENTARY-PROCEDURES-CLASS-1 NGAP-ELEMENTARY-PROCEDURE ::= {

aMFConfigurationUpdate

|

broadcastSessionModification
|

broadcastSessionRelease

|

broadcastSessionSetup

|

broadcastSessionTransport

|

distributionSetup

|

distributionRelease

|

handoverCancel

|

handoverPreparation

|

handoverResourceAllocation
|

initialContextSetup

|

mTCommunicationHandling

|

multicastSessionActivation

|

multicastSessionDeactivation

|

multicastSessionUpdate

|

nGReset

|

nGSetup

|

pathSwitchRequest

|

pDUSessionResourceModify

|

pDUSessionResourceModifyIndication

|

pDUSessionResourceRelease

|

pDUSessionResourceSetup

|

pWSCancel

|

rANConfigurationUpdate

|

timingSynchronisationStatus
|

uEContextModification

|

uEContextRelease

|

uEContextResume

|

uEContextSuspend

|

uERadioCapabilityCheck

|

uERadioCapabilityIDMapping
|

writeReplaceWarning

|

nGRemoval

|

inventoryRequest

|

commandRequest

|

aIOTSessionRelease

,

...
}

NGAP-ELEMENTARY-PROCEDURES-CLASS-2 NGAP-ELEMENTARY-PROCEDURE ::= {

aMFCPRelocationIndication

|

aMFStatusIndication

|

broadcastSessionReleaseRequired
|

cellTrafficTrace

|

connectionEstablishmentIndication
|

deactivateTrace

|

downlinkNASTransport

|

downlinkNonUEAssociatedNRPPaTransport

|

downlinkRANConfigurationTransfer
|

downlinkRANEarlyStatusTransfer
|

downlinkRANStatusTransfer

|

downlinkRIMInformationTransfer

|

downlinkUEAssociatedNRPPaTransport

|

errorIndication

|

handoverNotification

|

handoverSuccess

|

initialUEMessage

|

locationReport

|

locationReportingControl

|

locationReportingFailureIndication
|

multicastGroupPaging

|

nASNonDeliveryIndication

|

overloadStart

|

overloadStop

|

paging

|

pDUSessionResourceNotify

|

privateMessage

|

pWSFailureIndication

|

pWSRestartIndication

|

rANCPRelocationIndication

|

rANPagingRequest

|

rerouteNASRequest

|

retrieveUEInformation

|

rRCInactiveTransitionReport

|

secondaryRATDataUsageReport
|

timingSynchronisationStatusReport
|

traceFailureIndication

|

traceStart

|

uEContextReleaseRequest

|

uEInformationTransfer

|

uERadioCapabilityInfoIndication
|

uETNLABindingRelease

|

uplinkNASTransport

|

uplinkNonUEAssociatedNRPPaTransport
|

uplinkRANConfigurationTransfer
|

uplinkRANEarlyStatusTransfer

|

uplinkRANStatusTransfer

|

uplinkRIMInformationTransfer

|

uplinkUEAssociatedNRPPaTransport

|

inventoryReport

|

aIOTSessionReleaseRequest

,

...

}

-- **************************************************************
--

-- Interface Elementary Procedures
--
-- **************************************************************

aMFConfigurationUpdate NGAP-ELEMENTARY-PROCEDURE ::= {

INITIATING MESSAGE
AMFConfigurationUpdate

SUCCESSFUL OUTCOME
AMFConfigurationUpdateAcknowledge

UNSUCCESSFUL OUTCOME
AMFConfigurationUpdateFailure

PROCEDURE CODE

id-AMFConfigurationUpdate

CRITICALITY

reject
}

aMFCPRelocationIndication NGAP-ELEMENTARY-PROCEDURE ::= {

INITIATING MESSAGE
AMFCPRelocationIndication

PROCEDURE CODE

id-AMFCPRelocationIndication

CRITICALITY

reject
}

aMFStatusIndication NGAP-ELEMENTARY-PROCEDURE ::={

INITIATING MESSAGE
AMFStatusIndication

PROCEDURE CODE

id-AMFStatusIndication

CRITICALITY

ignore
}

broadcastSessionModification NGAP-ELEMENTARY-PROCEDURE ::= {

INITIATING MESSAGE
BroadcastSessionModificationRequest

SUCCESSFUL OUTCOME
BroadcastSessionModificationResponse

UNSUCCESSFUL OUTCOME
BroadcastSessionModificationFailure

PROCEDURE CODE

id-BroadcastSessionModification

CRITICALITY

reject
}

broadcastSessionRelease NGAP-ELEMENTARY-PROCEDURE ::= {

INITIATING MESSAGE
BroadcastSessionReleaseRequest

SUCCESSFUL OUTCOME
BroadcastSessionReleaseResponse

PROCEDURE CODE

id-BroadcastSessionRelease

CRITICALITY

reject
}

broadcastSessionReleaseRequired NGAP-ELEMENTARY-PROCEDURE ::= {

INITIATING MESSAGE
BroadcastSessionReleaseRequired

PROCEDURE CODE

id-BroadcastSessionReleaseRequired

CRITICALITY

reject
}

broadcastSessionSetup NGAP-ELEMENTARY-PROCEDURE ::= {

INITIATING MESSAGE
BroadcastSessionSetupRequest

SUCCESSFUL OUTCOME
BroadcastSessionSetupResponse

UNSUCCESSFUL OUTCOME
BroadcastSessionSetupFailure

PROCEDURE CODE

id-BroadcastSessionSetup

CRITICALITY

reject
}

broadcastSessionTransport NGAP-ELEMENTARY-PROCEDURE ::= {

INITIATING MESSAGE
BroadcastSessionTransportRequest

SUCCESSFUL OUTCOME
BroadcastSessionTransportResponse

UNSUCCESSFUL OUTCOME
BroadcastSessionTransportFailure

PROCEDURE CODE

id-BroadcastSessionTransport

CRITICALITY

reject
}

cellTrafficTrace NGAP-ELEMENTARY-PROCEDURE ::={

INITIATING MESSAGE
CellTrafficTrace

PROCEDURE CODE

id-CellTrafficTrace

CRITICALITY

ignore
}

connectionEstablishmentIndication NGAP-ELEMENTARY-PROCEDURE ::= {

INITIATING MESSAGE
ConnectionEstablishmentIndication

PROCEDURE CODE

id-ConnectionEstablishmentIndication

CRITICALITY

reject
}

deactivateTrace NGAP-ELEMENTARY-PROCEDURE ::= {

INITIATING MESSAGE
DeactivateTrace

PROCEDURE CODE

id-DeactivateTrace

CRITICALITY

ignore
}

distributionSetup NGAP-ELEMENTARY-PROCEDURE ::= {

INITIATING MESSAGE
DistributionSetupRequest

SUCCESSFUL OUTCOME
DistributionSetupResponse

UNSUCCESSFUL OUTCOME
DistributionSetupFailure

PROCEDURE CODE

id-DistributionSetup

CRITICALITY

reject
}

distributionRelease NGAP-ELEMENTARY-PROCEDURE ::= {

INITIATING MESSAGE
DistributionReleaseRequest

SUCCESSFUL OUTCOME
DistributionReleaseResponse

PROCEDURE CODE

id-DistributionRelease

CRITICALITY

reject
}

downlinkNASTransport NGAP-ELEMENTARY-PROCEDURE ::= {

INITIATING MESSAGE
DownlinkNASTransport

PROCEDURE CODE

id-DownlinkNASTransport

CRITICALITY

ignore
}

downlinkNonUEAssociatedNRPPaTransport NGAP-ELEMENTARY-PROCEDURE ::= {

INITIATING MESSAGE
DownlinkNonUEAssociatedNRPPaTransport

PROCEDURE CODE

id-DownlinkNonUEAssociatedNRPPaTransport

CRITICALITY

ignore
}

downlinkRANConfigurationTransfer NGAP-ELEMENTARY-PROCEDURE ::= {

INITIATING MESSAGE
DownlinkRANConfigurationTransfer

PROCEDURE CODE

id-DownlinkRANConfigurationTransfer

CRITICALITY

ignore
}

downlinkRANEarlyStatusTransfer NGAP-ELEMENTARY-PROCEDURE ::= {

INITIATING MESSAGE
DownlinkRANEarlyStatusTransfer

PROCEDURE CODE

id-DownlinkRANEarlyStatusTransfer

CRITICALITY

ignore
}

downlinkRANStatusTransfer NGAP-ELEMENTARY-PROCEDURE ::= {

INITIATING MESSAGE
DownlinkRANStatusTransfer

PROCEDURE CODE

id-DownlinkRANStatusTransfer

CRITICALITY

ignore
}

downlinkUEAssociatedNRPPaTransport NGAP-ELEMENTARY-PROCEDURE ::= {

INITIATING MESSAGE
DownlinkUEAssociatedNRPPaTransport

PROCEDURE CODE

id-DownlinkUEAssociatedNRPPaTransport

CRITICALITY

ignore
}

errorIndication NGAP-ELEMENTARY-PROCEDURE ::= {

INITIATING MESSAGE
ErrorIndication

PROCEDURE CODE

id-ErrorIndication

CRITICALITY

ignore
}

handoverCancel NGAP-ELEMENTARY-PROCEDURE ::= {

INITIATING MESSAGE
HandoverCancel

SUCCESSFUL OUTCOME
HandoverCancelAcknowledge

PROCEDURE CODE

id-HandoverCancel

CRITICALITY

reject
}

handoverNotification NGAP-ELEMENTARY-PROCEDURE ::= {

INITIATING MESSAGE
HandoverNotify

PROCEDURE CODE

id-HandoverNotification

CRITICALITY

ignore
}

handoverPreparation NGAP-ELEMENTARY-PROCEDURE ::= {

INITIATING MESSAGE
HandoverRequired

SUCCESSFUL OUTCOME
HandoverCommand

UNSUCCESSFUL OUTCOME
HandoverPreparationFailure

PROCEDURE CODE

id-HandoverPreparation

CRITICALITY

reject
}

handoverResourceAllocation NGAP-ELEMENTARY-PROCEDURE ::= {

INITIATING MESSAGE
HandoverRequest

SUCCESSFUL OUTCOME
HandoverRequestAcknowledge

UNSUCCESSFUL OUTCOME
HandoverFailure

PROCEDURE CODE

id-HandoverResourceAllocation

CRITICALITY

reject
}

handoverSuccess NGAP-ELEMENTARY-PROCEDURE ::= {

INITIATING MESSAGE
HandoverSuccess

PROCEDURE CODE

id-HandoverSuccess

CRITICALITY

ignore
}

initialContextSetup NGAP-ELEMENTARY-PROCEDURE ::= {

INITIATING MESSAGE
InitialContextSetupRequest

SUCCESSFUL OUTCOME
InitialContextSetupResponse

UNSUCCESSFUL OUTCOME
InitialContextSetupFailure

PROCEDURE CODE

id-InitialContextSetup

CRITICALITY

reject
}

initialUEMessage NGAP-ELEMENTARY-PROCEDURE ::= {

INITIATING MESSAGE
InitialUEMessage

PROCEDURE CODE

id-InitialUEMessage

CRITICALITY

ignore
}

locationReport NGAP-ELEMENTARY-PROCEDURE ::= {

INITIATING MESSAGE
LocationReport

PROCEDURE CODE

id-LocationReport

CRITICALITY

ignore
}

locationReportingControl NGAP-ELEMENTARY-PROCEDURE ::= {

INITIATING MESSAGE
LocationReportingControl

PROCEDURE CODE

id-LocationReportingControl

CRITICALITY

ignore
}

locationReportingFailureIndication NGAP-ELEMENTARY-PROCEDURE ::= {

INITIATING MESSAGE
LocationReportingFailureIndication

PROCEDURE CODE

id-LocationReportingFailureIndication

CRITICALITY

ignore
}

mTCommunicationHandling NGAP-ELEMENTARY-PROCEDURE ::= {

INITIATING MESSAGE
MTCommunicationHandlingRequest

SUCCESSFUL OUTCOME
MTCommunicationHandlingResponse

UNSUCCESSFUL OUTCOME
MTCommunicationHandlingFailure

PROCEDURE CODE

id-MTCommunicationHandling

CRITICALITY

reject
}

multicastSessionActivation NGAP-ELEMENTARY-PROCEDURE ::= {

INITIATING MESSAGE
MulticastSessionActivationRequest

SUCCESSFUL OUTCOME
MulticastSessionActivationResponse

UNSUCCESSFUL OUTCOME
MulticastSessionActivationFailure

PROCEDURE CODE

id-MulticastSessionActivation

CRITICALITY

reject
}

multicastSessionDeactivation NGAP-ELEMENTARY-PROCEDURE ::= {

INITIATING MESSAGE
MulticastSessionDeactivationRequest

SUCCESSFUL OUTCOME
MulticastSessionDeactivationResponse

PROCEDURE CODE

id-MulticastSessionDeactivation

CRITICALITY

reject
}

multicastSessionUpdate NGAP-ELEMENTARY-PROCEDURE ::= {

INITIATING MESSAGE
MulticastSessionUpdateRequest

SUCCESSFUL OUTCOME
MulticastSessionUpdateResponse

UNSUCCESSFUL OUTCOME
MulticastSessionUpdateFailure

PROCEDURE CODE

id-MulticastSessionUpdate

CRITICALITY

reject
}

multicastGroupPaging

NGAP-ELEMENTARY-PROCEDURE ::= {

INITIATING MESSAGE
MulticastGroupPaging

PROCEDURE CODE

id-MulticastGroupPaging

CRITICALITY

ignore
}

nASNonDeliveryIndication NGAP-ELEMENTARY-PROCEDURE ::= {

INITIATING MESSAGE
NASNonDeliveryIndication

PROCEDURE CODE

id-NASNonDeliveryIndication

CRITICALITY

ignore
}

nGReset NGAP-ELEMENTARY-PROCEDURE ::= {

INITIATING MESSAGE
NGReset

SUCCESSFUL OUTCOME
NGResetAcknowledge

PROCEDURE CODE

id-NGReset

CRITICALITY

reject
}

nGSetup NGAP-ELEMENTARY-PROCEDURE ::= {

INITIATING MESSAGE
NGSetupRequest

SUCCESSFUL OUTCOME
NGSetupResponse

UNSUCCESSFUL OUTCOME
NGSetupFailure

PROCEDURE CODE

id-NGSetup

CRITICALITY

reject
}

nGRemoval NGAP-ELEMENTARY-PROCEDURE ::= {

INITIATING MESSAGE
NGRemovalRequest

SUCCESSFUL OUTCOME
NGRemovalResponse

UNSUCCESSFUL OUTCOME
NGRemovalFailure

PROCEDURE CODE

id-NGRemoval

CRITICALITY

reject
}

overloadStart NGAP-ELEMENTARY-PROCEDURE ::= {

INITIATING MESSAGE
OverloadStart

PROCEDURE CODE

id-OverloadStart

CRITICALITY

ignore
}

overloadStop NGAP-ELEMENTARY-PROCEDURE ::= {

INITIATING MESSAGE
OverloadStop

PROCEDURE CODE

id-OverloadStop

CRITICALITY

reject
}

paging NGAP-ELEMENTARY-PROCEDURE ::= {

INITIATING MESSAGE
Paging

PROCEDURE CODE

id-Paging

CRITICALITY

ignore
}

pathSwitchRequest NGAP-ELEMENTARY-PROCEDURE ::= {

INITIATING MESSAGE
PathSwitchRequest

SUCCESSFUL OUTCOME
PathSwitchRequestAcknowledge

UNSUCCESSFUL OUTCOME
PathSwitchRequestFailure

PROCEDURE CODE

id-PathSwitchRequest

CRITICALITY

reject
}

pDUSessionResourceModify NGAP-ELEMENTARY-PROCEDURE ::= {

INITIATING MESSAGE
PDUSessionResourceModifyRequest

SUCCESSFUL OUTCOME
PDUSessionResourceModifyResponse

PROCEDURE CODE

id-PDUSessionResourceModify

CRITICALITY

reject
}

pDUSessionResourceModifyIndication NGAP-ELEMENTARY-PROCEDURE ::= {

INITIATING MESSAGE
PDUSessionResourceModifyIndication

SUCCESSFUL OUTCOME
PDUSessionResourceModifyConfirm

PROCEDURE CODE

id-PDUSessionResourceModifyIndication

CRITICALITY

reject
}

pDUSessionResourceNotify NGAP-ELEMENTARY-PROCEDURE ::= {

INITIATING MESSAGE
PDUSessionResourceNotify

PROCEDURE CODE

id-PDUSessionResourceNotify

CRITICALITY

ignore
}

pDUSessionResourceRelease NGAP-ELEMENTARY-PROCEDURE ::= {

INITIATING MESSAGE
PDUSessionResourceReleaseCommand

SUCCESSFUL OUTCOME
PDUSessionResourceReleaseResponse

PROCEDURE CODE

id-PDUSessionResourceRelease

CRITICALITY

reject
}

pDUSessionResourceSetup NGAP-ELEMENTARY-PROCEDURE ::= {

INITIATING MESSAGE
PDUSessionResourceSetupRequest

SUCCESSFUL OUTCOME
PDUSessionResourceSetupResponse

PROCEDURE CODE

id-PDUSessionResourceSetup

CRITICALITY

reject
}

privateMessage NGAP-ELEMENTARY-PROCEDURE ::= {

INITIATING MESSAGE
PrivateMessage

PROCEDURE CODE

id-PrivateMessage

CRITICALITY

ignore
}

pWSCancel NGAP-ELEMENTARY-PROCEDURE ::= {

INITIATING MESSAGE
PWSCancelRequest

SUCCESSFUL OUTCOME
PWSCancelResponse

PROCEDURE CODE

id-PWSCancel

CRITICALITY

reject
}

pWSFailureIndication NGAP-ELEMENTARY-PROCEDURE ::= {

INITIATING MESSAGE
PWSFailureIndication

PROCEDURE CODE

id-PWSFailureIndication

CRITICALITY

ignore
}

pWSRestartIndication NGAP-ELEMENTARY-PROCEDURE ::= {

INITIATING MESSAGE
PWSRestartIndication

PROCEDURE CODE

id-PWSRestartIndication

CRITICALITY

ignore
}

rANConfigurationUpdate NGAP-ELEMENTARY-PROCEDURE ::= {

INITIATING MESSAGE
RANConfigurationUpdate

SUCCESSFUL OUTCOME
RANConfigurationUpdateAcknowledge

UNSUCCESSFUL OUTCOME
RANConfigurationUpdateFailure

PROCEDURE CODE

id-RANConfigurationUpdate

CRITICALITY

reject
}

rANCPRelocationIndication NGAP-ELEMENTARY-PROCEDURE ::= {

INITIATING MESSAGE
RANCPRelocationIndication

PROCEDURE CODE

id-RANCPRelocationIndication

CRITICALITY

reject
}

rANPagingRequest NGAP-ELEMENTARY-PROCEDURE ::= {

INITIATING MESSAGE
RANPagingRequest

PROCEDURE CODE

id-RANPagingRequest

CRITICALITY

ignore
}

rerouteNASRequest NGAP-ELEMENTARY-PROCEDURE ::= {

INITIATING MESSAGE
RerouteNASRequest

PROCEDURE CODE

id-RerouteNASRequest

CRITICALITY

reject

}

retrieveUEInformation NGAP-ELEMENTARY-PROCEDURE ::= {

INITIATING MESSAGE
RetrieveUEInformation

PROCEDURE CODE

id-RetrieveUEInformation

CRITICALITY

reject
}

rRCInactiveTransitionReport NGAP-ELEMENTARY-PROCEDURE ::= {

INITIATING MESSAGE
RRCInactiveTransitionReport

PROCEDURE CODE

id-RRCInactiveTransitionReport

CRITICALITY

ignore
}

secondaryRATDataUsageReport NGAP-ELEMENTARY-PROCEDURE ::= {

INITIATING MESSAGE
SecondaryRATDataUsageReport

PROCEDURE CODE

id-SecondaryRATDataUsageReport

CRITICALITY

ignore
}

timingSynchronisationStatus NGAP-ELEMENTARY-PROCEDURE ::= {

INITIATING MESSAGE
TimingSynchronisationStatusRequest

SUCCESSFUL OUTCOME
TimingSynchronisationStatusResponse

UNSUCCESSFUL OUTCOME
TimingSynchronisationStatusFailure

PROCEDURE CODE

id-TimingSynchronisationStatus

CRITICALITY

reject
}

timingSynchronisationStatusReport NGAP-ELEMENTARY-PROCEDURE ::= {

INITIATING MESSAGE
TimingSynchronisationStatusReport

PROCEDURE CODE

id-TimingSynchronisationStatusReport

CRITICALITY

ignore
}

traceFailureIndication NGAP-ELEMENTARY-PROCEDURE ::= {

INITIATING MESSAGE
TraceFailureIndication

PROCEDURE CODE

id-TraceFailureIndication

CRITICALITY

ignore
}

traceStart NGAP-ELEMENTARY-PROCEDURE ::= {

INITIATING MESSAGE
TraceStart

PROCEDURE CODE

id-TraceStart

CRITICALITY

ignore
}

uEContextModification NGAP-ELEMENTARY-PROCEDURE ::= {

INITIATING MESSAGE
UEContextModificationRequest

SUCCESSFUL OUTCOME
UEContextModificationResponse

UNSUCCESSFUL OUTCOME
UEContextModificationFailure

PROCEDURE CODE

id-UEContextModification

CRITICALITY

reject
}

uEContextRelease NGAP-ELEMENTARY-PROCEDURE ::= {

INITIATING MESSAGE
UEContextReleaseCommand

SUCCESSFUL OUTCOME
UEContextReleaseComplete

PROCEDURE CODE

id-UEContextRelease

CRITICALITY

reject
}

uEContextReleaseRequest NGAP-ELEMENTARY-PROCEDURE ::= {

INITIATING MESSAGE
UEContextReleaseRequest

PROCEDURE CODE

id-UEContextReleaseRequest

CRITICALITY

ignore
}

uEContextResume NGAP-ELEMENTARY-PROCEDURE ::= {

INITIATING MESSAGE
UEContextResumeRequest

SUCCESSFUL OUTCOME
UEContextResumeResponse

UNSUCCESSFUL OUTCOME
UEContextResumeFailure

PROCEDURE CODE

id-UEContextResume

CRITICALITY

reject
}

uEContextSuspend NGAP-ELEMENTARY-PROCEDURE ::= {

INITIATING MESSAGE
UEContextSuspendRequest

SUCCESSFUL OUTCOME
UEContextSuspendResponse

UNSUCCESSFUL OUTCOME
UEContextSuspendFailure

PROCEDURE CODE

id-UEContextSuspend

CRITICALITY

reject
}

uEInformationTransfer NGAP-ELEMENTARY-PROCEDURE ::= {

INITIATING MESSAGE
UEInformationTransfer

PROCEDURE CODE

id-UEInformationTransfer

CRITICALITY

reject
}

uERadioCapabilityCheck NGAP-ELEMENTARY-PROCEDURE ::= {

INITIATING MESSAGE
UERadioCapabilityCheckRequest

SUCCESSFUL OUTCOME
UERadioCapabilityCheckResponse

PROCEDURE CODE

id-UERadioCapabilityCheck

CRITICALITY

reject
}

uERadioCapabilityIDMapping NGAP-ELEMENTARY-PROCEDURE ::= {

INITIATING MESSAGE
UERadioCapabilityIDMappingRequest

SUCCESSFUL OUTCOME
UERadioCapabilityIDMappingResponse

PROCEDURE CODE

id-UERadioCapabilityIDMapping

CRITICALITY

reject
}

uERadioCapabilityInfoIndication NGAP-ELEMENTARY-PROCEDURE ::= {

INITIATING MESSAGE
UERadioCapabilityInfoIndication

PROCEDURE CODE

id-UERadioCapabilityInfoIndication

CRITICALITY

ignore
}

uETNLABindingRelease NGAP-ELEMENTARY-PROCEDURE ::= {

INITIATING MESSAGE
UETNLABindingReleaseRequest

PROCEDURE CODE

id-UETNLABindingRelease

CRITICALITY

ignore
}

uplinkNASTransport NGAP-ELEMENTARY-PROCEDURE ::= {

INITIATING MESSAGE
UplinkNASTransport

PROCEDURE CODE

id-UplinkNASTransport

CRITICALITY

ignore
}

uplinkNonUEAssociatedNRPPaTransport NGAP-ELEMENTARY-PROCEDURE ::= {

INITIATING MESSAGE
UplinkNonUEAssociatedNRPPaTransport

PROCEDURE CODE

id-UplinkNonUEAssociatedNRPPaTransport

CRITICALITY

ignore
}

uplinkRANConfigurationTransfer NGAP-ELEMENTARY-PROCEDURE ::= {

INITIATING MESSAGE
UplinkRANConfigurationTransfer

PROCEDURE CODE

id-UplinkRANConfigurationTransfer

CRITICALITY

ignore
}

uplinkRANEarlyStatusTransfer NGAP-ELEMENTARY-PROCEDURE ::= {

INITIATING MESSAGE
UplinkRANEarlyStatusTransfer

PROCEDURE CODE

id-UplinkRANEarlyStatusTransfer

CRITICALITY

reject
}

uplinkRANStatusTransfer NGAP-ELEMENTARY-PROCEDURE ::= {

INITIATING MESSAGE
UplinkRANStatusTransfer

PROCEDURE CODE

id-UplinkRANStatusTransfer

CRITICALITY

ignore
}

uplinkUEAssociatedNRPPaTransport NGAP-ELEMENTARY-PROCEDURE ::= {

INITIATING MESSAGE
UplinkUEAssociatedNRPPaTransport

PROCEDURE CODE

id-UplinkUEAssociatedNRPPaTransport

CRITICALITY

ignore
}

writeReplaceWarning NGAP-ELEMENTARY-PROCEDURE ::= {

INITIATING MESSAGE
WriteReplaceWarningRequest

SUCCESSFUL OUTCOME
WriteReplaceWarningResponse

PROCEDURE CODE

id-WriteReplaceWarning

CRITICALITY

reject
}

uplinkRIMInformationTransfer NGAP-ELEMENTARY-PROCEDURE ::= {

INITIATING MESSAGE
UplinkRIMInformationTransfer

PROCEDURE CODE

id-UplinkRIMInformationTransfer

CRITICALITY

ignore

}

downlinkRIMInformationTransfer NGAP-ELEMENTARY-PROCEDURE ::= {

INITIATING MESSAGE
DownlinkRIMInformationTransfer

PROCEDURE CODE

id-DownlinkRIMInformationTransfer

CRITICALITY

ignore
}

inventoryRequest NGAP-ELEMENTARY-PROCEDURE ::= {

INITIATING MESSAGE
InventoryRequest

SUCCESSFUL OUTCOME
InventoryResponse

UNSUCCESSFUL OUTCOME
InventoryFailure

PROCEDURE CODE

id-InventoryRequest

CRITICALITY

reject
}

inventoryReport NGAP-ELEMENTARY-PROCEDURE ::= {

INITIATING MESSAGE
InventoryReport

PROCEDURE CODE

id-InventoryReport

CRITICALITY

reject
}

commandRequest NGAP-ELEMENTARY-PROCEDURE ::= {

INITIATING MESSAGE
CommandRequest

SUCCESSFUL OUTCOME
CommandResponse

UNSUCCESSFUL OUTCOME
CommandFailure

PROCEDURE CODE

id-CommandRequest

CRITICALITY

reject
}

aIOTSessionRelease NGAP-ELEMENTARY-PROCEDURE ::= {

INITIATING MESSAGE
AIOTSessionReleaseCommand

SUCCESSFUL OUTCOME
AIOTSessionReleaseComplete

PROCEDURE CODE

id-AIOTSessionRelease

CRITICALITY

reject
}

aIOTSessionReleaseRequest NGAP-ELEMENTARY-PROCEDURE ::= {

INITIATING MESSAGE
AIOTSessionReleaseRequest

PROCEDURE CODE

id-AIOTSessionReleaseRequest

CRITICALITY

reject
}

END
-- ASN1STOP
